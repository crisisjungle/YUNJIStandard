--
-- TENCENT-TMDC-MIB_V3.0.6.mib
-- MIB generated by MG-SOFT Visual MIB Builder Version 6.0  Build 88
-- Monday, July 01, 2019 at 13:12:34
--

--  TENCENT-TMDC-MIB_v2.0.2£¨Ìì½ò-»ú¼ÜÄæ±äÆ÷£©.mib
-- MIB generated by MG-SOFT Visual MIB Builder Version 6.0  Build 88
-- Tuesday, May 10, 2016 at 19:53:32
-- 
--  TENCENT-TMDC-MIB_V2.0.mib
-- MIB generated by MG-SOFT Visual MIB Builder Version 6.0  Build 88
-- Wednesday, November 12, 2014 at 17:27:00
-- 
--  TENCENT-TMDC-MIB1.mib
-- MIB generated by MG-SOFT Visual MIB Builder Version 5.0  Build 250
-- Thursday, August 01, 2013 at 19:16:13
-- 
--  TENCENT-TMDC-MIB_V1.0.0723.mib
-- MIB generated by MG-SOFT Visual MIB Builder Version 6.0  Build 88
-- Thursday, July 25, 2013 at 18:34:54
-- 

	TENCENT-TMDC-MIB DEFINITIONS ::= BEGIN
 
		IMPORTS
			enterprises, Integer32, OBJECT-TYPE, OBJECT-IDENTITY, NOTIFICATION-TYPE			
				FROM SNMPv2-SMI			
			DisplayString, TEXTUAL-CONVENTION			
				FROM SNMPv2-TC;
	
	
--
-- Textual conventions
--
	
		AlarmLevel ::= TEXTUAL-CONVENTION
			STATUS current
			DESCRIPTION 
				"information(1)
				warning(2)
				minor(3)
				major(4)
				critical(5)
				"
			SYNTAX INTEGER
				{
				information(1),
				warning(2),
				minor(3),
				major(4),
				critical(5)
				}

	
--
-- Node definitions
--
	
--  Node definitions
-- 
-- Node definitions
-- 
-- Node definitions
-- 
-- Node definitions
-- 
-- 1.3.6.1.4.1.41475
-- 1.3.6.1.4.1.41475
-- 1.3.6.1.4.1.41475
-- 1.3.6.1.4.1.41475
		-- 1.3.6.1.4.1.41475
		tencent OBJECT-IDENTITY
			STATUS current
			DESCRIPTION 
				"The root of the OID sub-tree assigned to Company by the Internet Assigned Numbers Authority (IANA)"
			::= { enterprises 41475 }

		
--     1.3.6.1.4.1.41475.3
-- 1.3.6.1.4.1.41475.3
-- 1.3.6.1.4.1.41475.3
-- 1.3.6.1.4.1.41475.3
		-- 1.3.6.1.4.1.41475.3
		products OBJECT-IDENTITY
			STATUS current
			DESCRIPTION 
				"Sub-tree for specific object and event definitions"
			::= { tencent 3 }

		
--     1.3.6.1.4.1.41475.3.1
-- 1.3.6.1.4.1.41475.3.1
-- 1.3.6.1.4.1.41475.3.1
-- 1.3.6.1.4.1.41475.3.1
		-- 1.3.6.1.4.1.41475.3.1
		tmdc OBJECT-IDENTITY
			STATUS current
			DESCRIPTION 
				"Description: Tencent MDC."
			::= { products 1 }

		
--     1.3.6.1.4.1.41475.3.1.2
-- 1.3.6.1.4.1.41475.3.1.2
-- 1.3.6.1.4.1.41475.3.1.1
-- 1.3.6.1.4.1.41475.3.1.1
		-- 1.3.6.1.4.1.41475.3.1.1
		tmdcSystem OBJECT IDENTIFIER ::= { tmdc 1 }

		
--     1.3.6.1.4.1.41475.3.1.2.1
-- 1.3.6.1.4.1.41475.3.1.2.1
-- 1.3.6.1.4.1.41475.3.1.1.1
-- 1.3.6.1.4.1.41475.3.1.1.1
		-- 1.3.6.1.4.1.41475.3.1.1.1
		tmdcSysName OBJECT-TYPE
			SYNTAX DisplayString
			MAX-ACCESS read-only
			STATUS current
			DESCRIPTION
				"Description: MDC system name. "
			::= { tmdcSystem 1 }

		
--   
-- 
-- 1.3.6.1.4.1.41475.3.1.2.2
-- 1.3.6.1.4.1.41475.3.1.2.2
-- 1.3.6.1.4.1.41475.3.1.1.2
-- 1.3.6.1.4.1.41475.3.1.1.2
		-- 1.3.6.1.4.1.41475.3.1.1.2
		tmdcSysDesc OBJECT-TYPE
			SYNTAX DisplayString
			MAX-ACCESS read-only
			STATUS current
			DESCRIPTION
				"Description: MDC system description."
			::= { tmdcSystem 2 }

		
--     1.3.6.1.4.1.41475.3.1.2.3
-- 1.3.6.1.4.1.41475.3.1.2.3
-- 1.3.6.1.4.1.41475.3.1.1.3
-- 1.3.6.1.4.1.41475.3.1.1.3
		-- 1.3.6.1.4.1.41475.3.1.1.3
		tmdcSysLocation OBJECT-TYPE
			SYNTAX DisplayString
			MAX-ACCESS read-only
			STATUS current
			DESCRIPTION
				"Description: The location of the MDC, using IDC encoding: room number-MDC number."
			::= { tmdcSystem 3 }

		
--     1.3.6.1.4.1.41475.3.1.2.4
-- 1.3.6.1.4.1.41475.3.1.2.4
-- 1.3.6.1.4.1.41475.3.1.1.4
-- 1.3.6.1.4.1.41475.3.1.1.4
		-- 1.3.6.1.4.1.41475.3.1.1.4
		tmdcSysManufacturer OBJECT-TYPE
			SYNTAX DisplayString
			MAX-ACCESS read-only
			STATUS current
			DESCRIPTION
				"Description: MDC manufacturer."
			::= { tmdcSystem 4 }

		
--     1.3.6.1.4.1.41475.3.1.2.6
-- 1.3.6.1.4.1.41475.3.1.2.6
-- 1.3.6.1.4.1.41475.3.1.1.5
-- 1.3.6.1.4.1.41475.3.1.1.5
		-- 1.3.6.1.4.1.41475.3.1.1.5
		tmdcSysTime OBJECT-TYPE
			SYNTAX DisplayString
			MAX-ACCESS read-only
			STATUS current
			DESCRIPTION
				"Description: The current system time.
				eg. 20100607T152000+08"
			::= { tmdcSystem 5 }

		
--     1.3.6.1.4.1.41475.3.1.2.7
-- 1.3.6.1.4.1.41475.3.1.2.7
-- 1.3.6.1.4.1.41475.3.1.1.6
-- 1.3.6.1.4.1.41475.3.1.1.6
		-- 1.3.6.1.4.1.41475.3.1.1.6
		tmdcEquipsTable OBJECT-TYPE
			SYNTAX SEQUENCE OF TmdcEquipsEntry
			MAX-ACCESS not-accessible
			STATUS current
			DESCRIPTION
				"Description."
			::= { tmdcSystem 6 }

		
--     1.3.6.1.4.1.41475.3.1.2.7.1
-- 1.3.6.1.4.1.41475.3.1.2.7.1
-- 1.3.6.1.4.1.41475.3.1.1.6.1
-- 1.3.6.1.4.1.41475.3.1.1.6.1
		-- 1.3.6.1.4.1.41475.3.1.1.6.1
		tmdcEquipsEntry OBJECT-TYPE
			SYNTAX TmdcEquipsEntry
			MAX-ACCESS not-accessible
			STATUS current
			DESCRIPTION
				"Description."
			INDEX { tmdcEquipsIndex }
			::= { tmdcEquipsTable 1 }

		
		TmdcEquipsEntry ::=
			SEQUENCE { 
				tmdcEquipsIndex
					Integer32,
				tmdcEquipClass
					DisplayString,
				tmdcEquipName
					DisplayString,
				tmdcEquipManufacturer
					DisplayString,
				tmdcEquipModel
					DisplayString,
				tmdcEquipCommStat
					DisplayString,
				tmdcEquipAlarmStat
					DisplayString,
				tmdcEquipTimestamp
					DisplayString
			 }

--     1.3.6.1.4.1.41475.3.1.2.7.1.1
-- 1.3.6.1.4.1.41475.3.1.2.7.1.1
-- 1.3.6.1.4.1.41475.3.1.1.6.1.1
-- 1.3.6.1.4.1.41475.3.1.1.6.1.1
		-- 1.3.6.1.4.1.41475.3.1.1.6.1.1
		tmdcEquipsIndex OBJECT-TYPE
			SYNTAX Integer32 (1..9999)
			MAX-ACCESS read-only
			STATUS current
			DESCRIPTION
				"Description: Equipment index. Used to uniquely identify a device. starting from 1."
			::= { tmdcEquipsEntry 1 }

		
--     1.3.6.1.4.1.41475.3.1.2.7.1.2
-- 1.3.6.1.4.1.41475.3.1.2.7.1.2
-- 1.3.6.1.4.1.41475.3.1.1.6.1.2
-- 1.3.6.1.4.1.41475.3.1.1.6.1.2
		-- 1.3.6.1.4.1.41475.3.1.1.6.1.2
		tmdcEquipClass OBJECT-TYPE
			SYNTAX DisplayString
			MAX-ACCESS read-only
			STATUS current
			DESCRIPTION
				"Description: The classification of equipment. As defined in the relevant conventions."
			::= { tmdcEquipsEntry 2 }

		
--     1.3.6.1.4.1.41475.3.1.2.7.1.3
-- 1.3.6.1.4.1.41475.3.1.2.7.1.3
-- 1.3.6.1.4.1.41475.3.1.1.6.1.3
-- 1.3.6.1.4.1.41475.3.1.1.6.1.3
		-- 1.3.6.1.4.1.41475.3.1.1.6.1.3
		tmdcEquipName OBJECT-TYPE
			SYNTAX DisplayString
			MAX-ACCESS read-only
			STATUS current
			DESCRIPTION
				"Description: The device name."
			::= { tmdcEquipsEntry 3 }

		
--     1.3.6.1.4.1.41475.3.1.2.7.1.5
-- 1.3.6.1.4.1.41475.3.1.2.7.1.5
-- 1.3.6.1.4.1.41475.3.1.1.6.1.4
-- 1.3.6.1.4.1.41475.3.1.1.6.1.4
		-- 1.3.6.1.4.1.41475.3.1.1.6.1.4
		tmdcEquipManufacturer OBJECT-TYPE
			SYNTAX DisplayString
			MAX-ACCESS read-only
			STATUS current
			DESCRIPTION
				"Description: Equipment manufacturers."
			::= { tmdcEquipsEntry 4 }

		
--     1.3.6.1.4.1.41475.3.1.2.7.1.6
-- 1.3.6.1.4.1.41475.3.1.2.7.1.6
-- 1.3.6.1.4.1.41475.3.1.1.6.1.5
-- 1.3.6.1.4.1.41475.3.1.1.6.1.5
		-- 1.3.6.1.4.1.41475.3.1.1.6.1.5
		tmdcEquipModel OBJECT-TYPE
			SYNTAX DisplayString
			MAX-ACCESS read-only
			STATUS current
			DESCRIPTION
				"Description: Equipment model."
			::= { tmdcEquipsEntry 5 }

		
--     1.3.6.1.4.1.41475.3.1.2.7.1.7
-- 1.3.6.1.4.1.41475.3.1.2.7.1.7
-- 1.3.6.1.4.1.41475.3.1.1.6.1.6
-- 1.3.6.1.4.1.41475.3.1.1.6.1.6
		-- 1.3.6.1.4.1.41475.3.1.1.6.1.6
		tmdcEquipCommStat OBJECT-TYPE
			SYNTAX DisplayString
			MAX-ACCESS read-only
			STATUS current
			DESCRIPTION
				"Description: Communication status.
				Values: 0-ok, 1-Interrupt"
			::= { tmdcEquipsEntry 6 }

		
--     1.3.6.1.4.1.41475.3.1.2.7.1.8
-- 1.3.6.1.4.1.41475.3.1.2.7.1.8
-- 1.3.6.1.4.1.41475.3.1.1.6.1.7
-- 1.3.6.1.4.1.41475.3.1.1.6.1.7
		-- 1.3.6.1.4.1.41475.3.1.1.6.1.7
		tmdcEquipAlarmStat OBJECT-TYPE
			SYNTAX DisplayString
			MAX-ACCESS read-only
			STATUS current
			DESCRIPTION
				"Description: Alarm status.
				Values: 0-ok, 1-Alarm"
			::= { tmdcEquipsEntry 7 }

		
--   1.3.6.1.4.1.41475.3.1.1.6.1.8
-- 1.3.6.1.4.1.41475.3.1.1.6.1.8
		-- 1.3.6.1.4.1.41475.3.1.1.6.1.8
		tmdcEquipTimestamp OBJECT-TYPE
			SYNTAX DisplayString
			MAX-ACCESS read-only
			STATUS current
			DESCRIPTION
				"Description: The timestamp of the last update.
				eg. 20100607T152000+08"
			::= { tmdcEquipsEntry 8 }

		
--     1.3.6.1.4.1.41475.3.1.3
-- 1.3.6.1.4.1.41475.3.1.3
-- 1.3.6.1.4.1.41475.3.1.2
-- 1.3.6.1.4.1.41475.3.1.2
		-- 1.3.6.1.4.1.41475.3.1.2
		tmdcAlarm OBJECT IDENTIFIER ::= { tmdc 2 }

		
--     1.3.6.1.4.1.41475.3.1.3.1
-- 1.3.6.1.4.1.41475.3.1.3.1
-- 1.3.6.1.4.1.41475.3.1.2.1
-- 1.3.6.1.4.1.41475.3.1.2.1
		-- 1.3.6.1.4.1.41475.3.1.2.1
		tmdcNotifications OBJECT IDENTIFIER ::= { tmdcAlarm 1 }

		
--     1.3.6.1.4.1.41475.3.1.3.1.1
-- 1.3.6.1.4.1.41475.3.1.3.1.1
-- 1.3.6.1.4.1.41475.3.1.2.1.1
-- 1.3.6.1.4.1.41475.3.1.2.1.1
		-- 1.3.6.1.4.1.41475.3.1.2.1.1
		tmdcAlarmTrapDefine NOTIFICATION-TYPE
			OBJECTS { tmdcAlarmTrapIndex, tmdcAlarmTrapEquipClass, tmdcAlarmTrapStatus, tmdcAlarmTrapEquipsIndex, tmdcAlarmTrapOid, 
				tmdcAlarmTrapLevel, tmdcAlarmTrapTime, tmdcAlarmTrapValue, tmdcAlarmTrapText, tmdcAlarmTrapUserAction
				 }
			STATUS current
			DESCRIPTION 
				"Description: trap oid."
			::= { tmdcNotifications 1 }

		
--     1.3.6.1.4.1.41475.3.1.3.1.2
-- 1.3.6.1.4.1.41475.3.1.3.1.2
-- 1.3.6.1.4.1.41475.3.1.2.1.2
-- 1.3.6.1.4.1.41475.3.1.2.1.2
		-- 1.3.6.1.4.1.41475.3.1.2.1.2
		tmdcAlarmTrapTable OBJECT-TYPE
			SYNTAX SEQUENCE OF TmdcAlarmTrapEntry
			MAX-ACCESS not-accessible
			STATUS current
			DESCRIPTION
				"Description."
			::= { tmdcNotifications 2 }

		
--     1.3.6.1.4.1.41475.3.1.3.1.2.1
-- 1.3.6.1.4.1.41475.3.1.3.1.2.1
-- 1.3.6.1.4.1.41475.3.1.2.1.2.1
-- 1.3.6.1.4.1.41475.3.1.2.1.2.1
		-- 1.3.6.1.4.1.41475.3.1.2.1.2.1
		tmdcAlarmTrapEntry OBJECT-TYPE
			SYNTAX TmdcAlarmTrapEntry
			MAX-ACCESS not-accessible
			STATUS current
			DESCRIPTION
				"Description."
			INDEX { tmdcAlarmTrapIndex }
			::= { tmdcAlarmTrapTable 1 }

		
		TmdcAlarmTrapEntry ::=
			SEQUENCE { 
				tmdcAlarmTrapIndex
					Integer32,
				tmdcAlarmTrapEquipClass
					DisplayString,
				tmdcAlarmTrapEquipsIndex
					DisplayString,
				tmdcAlarmTrapOid
					DisplayString,
				tmdcAlarmTrapStatus
					DisplayString,
				tmdcAlarmTrapLevel
					DisplayString,
				tmdcAlarmTrapTime
					DisplayString,
				tmdcAlarmTrapValue
					DisplayString,
				tmdcAlarmTrapText
					DisplayString,
				tmdcAlarmTrapUserAction
					DisplayString
			 }

--     1.3.6.1.4.1.41475.3.1.3.1.2.1.1
-- 1.3.6.1.4.1.41475.3.1.3.1.2.1.1
-- 1.3.6.1.4.1.41475.3.1.2.1.2.1.1
-- 1.3.6.1.4.1.41475.3.1.2.1.2.1.1
		-- 1.3.6.1.4.1.41475.3.1.2.1.2.1.1
		tmdcAlarmTrapIndex OBJECT-TYPE
			SYNTAX Integer32 (1..2147483647)
			MAX-ACCESS read-only
			STATUS current
			DESCRIPTION
				"Description: The serial number, starting from 1."
			::= { tmdcAlarmTrapEntry 1 }

		
--     1.3.6.1.4.1.41475.3.1.3.1.2.1.2
-- 1.3.6.1.4.1.41475.3.1.3.1.2.1.2
-- 1.3.6.1.4.1.41475.3.1.2.1.2.1.2
-- 1.3.6.1.4.1.41475.3.1.2.1.2.1.2
		-- 1.3.6.1.4.1.41475.3.1.2.1.2.1.2
		tmdcAlarmTrapEquipClass OBJECT-TYPE
			SYNTAX DisplayString
			MAX-ACCESS read-only
			STATUS current
			DESCRIPTION
				"Description: The classification of equipment. As defined in the relevant conventions."
			::= { tmdcAlarmTrapEntry 2 }

		
--     1.3.6.1.4.1.41475.3.1.3.1.2.1.3
-- 1.3.6.1.4.1.41475.3.1.3.1.2.1.3
-- 1.3.6.1.4.1.41475.3.1.2.1.2.1.3
-- 1.3.6.1.4.1.41475.3.1.2.1.2.1.3
		-- 1.3.6.1.4.1.41475.3.1.2.1.2.1.3
		tmdcAlarmTrapEquipsIndex OBJECT-TYPE
			SYNTAX DisplayString
			MAX-ACCESS read-only
			STATUS current
			DESCRIPTION
				"Description: Equipment index. Used to uniquely identify a device. starting from 1"
			::= { tmdcAlarmTrapEntry 3 }

		
--     1.3.6.1.4.1.41475.3.1.3.1.2.1.4
-- 1.3.6.1.4.1.41475.3.1.3.1.2.1.4
-- 1.3.6.1.4.1.41475.3.1.2.1.2.1.4
-- 1.3.6.1.4.1.41475.3.1.2.1.2.1.4
		-- 1.3.6.1.4.1.41475.3.1.2.1.2.1.4
		tmdcAlarmTrapOid OBJECT-TYPE
			SYNTAX DisplayString
			MAX-ACCESS read-only
			STATUS current
			DESCRIPTION
				"Description: Alarm object OID."
			::= { tmdcAlarmTrapEntry 4 }

		
--     Indicates 'activated' (0) or 'deactivated' (1) alarm events.
-- 1.3.6.1.4.1.41475.3.1.3.1.2.1.5
-- 1.3.6.1.4.1.41475.3.1.3.1.2.1.5
-- 1.3.6.1.4.1.41475.3.1.2.1.2.1.5
-- 1.3.6.1.4.1.41475.3.1.2.1.2.1.5
		-- 1.3.6.1.4.1.41475.3.1.2.1.2.1.5
		tmdcAlarmTrapStatus OBJECT-TYPE
			SYNTAX DisplayString
			MAX-ACCESS read-only
			STATUS current
			DESCRIPTION
				"Description: Alarm type
				Values: 0-alarm, 1-restore"
			::= { tmdcAlarmTrapEntry 5 }

		
--     1.3.6.1.4.1.41475.3.1.3.1.2.1.6
-- 1.3.6.1.4.1.41475.3.1.3.1.2.1.6
-- 1.3.6.1.4.1.41475.3.1.2.1.2.1.6
-- 1.3.6.1.4.1.41475.3.1.2.1.2.1.6
		-- 1.3.6.1.4.1.41475.3.1.2.1.2.1.6
		tmdcAlarmTrapLevel OBJECT-TYPE
			SYNTAX DisplayString
			MAX-ACCESS read-only
			STATUS current
			DESCRIPTION
				"Description: Alarm level, as defined in the relevant conventions."
			::= { tmdcAlarmTrapEntry 6 }

		
--     1.3.6.1.4.1.41475.3.1.3.1.2.1.7
-- 1.3.6.1.4.1.41475.3.1.3.1.2.1.7
-- 1.3.6.1.4.1.41475.3.1.2.1.2.1.7
-- 1.3.6.1.4.1.41475.3.1.2.1.2.1.7
		-- 1.3.6.1.4.1.41475.3.1.2.1.2.1.7
		tmdcAlarmTrapTime OBJECT-TYPE
			SYNTAX DisplayString
			MAX-ACCESS read-only
			STATUS current
			DESCRIPTION
				"Description: Alarm time."
			::= { tmdcAlarmTrapEntry 7 }

		
--   eg:2013-07-22 12:00:00
-- 1.3.6.1.4.1.41475.3.1.3.1.2.1.8
-- 1.3.6.1.4.1.41475.3.1.3.1.2.1.8
-- 1.3.6.1.4.1.41475.3.1.2.1.2.1.8
-- 1.3.6.1.4.1.41475.3.1.2.1.2.1.8
		-- 1.3.6.1.4.1.41475.3.1.2.1.2.1.8
		tmdcAlarmTrapValue OBJECT-TYPE
			SYNTAX DisplayString
			MAX-ACCESS read-only
			STATUS current
			DESCRIPTION
				"Description: Values in the alarm occurs."
			::= { tmdcAlarmTrapEntry 8 }

		
--     1.3.6.1.4.1.41475.3.1.3.1.2.1.9
-- 1.3.6.1.4.1.41475.3.1.3.1.2.1.9
-- 1.3.6.1.4.1.41475.3.1.2.1.2.1.9
-- 1.3.6.1.4.1.41475.3.1.2.1.2.1.9
		-- 1.3.6.1.4.1.41475.3.1.2.1.2.1.9
		tmdcAlarmTrapText OBJECT-TYPE
			SYNTAX DisplayString
			MAX-ACCESS read-only
			STATUS current
			DESCRIPTION
				"Description: Warning description information."
			::= { tmdcAlarmTrapEntry 9 }

		
--     1.3.6.1.4.1.41475.3.1.3.1.2.1.10
-- 1.3.6.1.4.1.41475.3.1.3.1.2.1.10
-- 1.3.6.1.4.1.41475.3.1.2.1.2.1.10
-- 1.3.6.1.4.1.41475.3.1.2.1.2.1.10
		-- 1.3.6.1.4.1.41475.3.1.2.1.2.1.10
		tmdcAlarmTrapUserAction OBJECT-TYPE
			SYNTAX DisplayString
			MAX-ACCESS read-only
			STATUS current
			DESCRIPTION
				"Description: Some suggestions for user handling."
			::= { tmdcAlarmTrapEntry 10 }

		
--     1.3.6.1.4.1.41475.3.1.4
-- 1.3.6.1.4.1.41475.3.1.4
-- 1.3.6.1.4.1.41475.3.1.3
-- 1.3.6.1.4.1.41475.3.1.3
		-- 1.3.6.1.4.1.41475.3.1.3
		tmdcStatistic OBJECT IDENTIFIER ::= { tmdc 3 }

		
--     1.3.6.1.4.1.41475.3.1.4.1
-- 1.3.6.1.4.1.41475.3.1.4.1
-- 1.3.6.1.4.1.41475.3.1.3.1
-- 1.3.6.1.4.1.41475.3.1.3.1
		-- 1.3.6.1.4.1.41475.3.1.3.1
		tmdcPUE OBJECT-TYPE
			SYNTAX DisplayString
			MAX-ACCESS read-only
			STATUS current
			DESCRIPTION
				"Description: The current PUE."
			::= { tmdcStatistic 1 }

		
--     1.3.6.1.4.1.41475.3.1.4.2
-- 1.3.6.1.4.1.41475.3.1.4.2
-- 1.3.6.1.4.1.41475.3.1.3.2
-- 1.3.6.1.4.1.41475.3.1.3.2
		-- 1.3.6.1.4.1.41475.3.1.3.2
		tmdcLoadIT OBJECT-TYPE
			SYNTAX DisplayString
			UNITS "kW"
			MAX-ACCESS read-only
			STATUS current
			DESCRIPTION
				"Description: The current system load."
			::= { tmdcStatistic 2 }

		
--     1.3.6.1.4.1.41475.3.1.4.2
-- 1.3.6.1.4.1.41475.3.1.4.2
-- 1.3.6.1.4.1.41475.3.1.3.3
-- 1.3.6.1.4.1.41475.3.1.3.3
		-- 1.3.6.1.4.1.41475.3.1.3.3
		tmdcLoadAll OBJECT-TYPE
			SYNTAX DisplayString
			UNITS "kW"
			MAX-ACCESS read-only
			STATUS current
			DESCRIPTION
				"Description: total load."
			::= { tmdcStatistic 3 }

		
--     1.3.6.1.4.1.41475.3.1.4.2
-- 1.3.6.1.4.1.41475.3.1.4.2
-- 1.3.6.1.4.1.41475.3.1.3.4
-- 1.3.6.1.4.1.41475.3.1.3.4
		-- 1.3.6.1.4.1.41475.3.1.3.4
		tmdcMaxPower OBJECT-TYPE
			SYNTAX DisplayString
			UNITS "kW"
			MAX-ACCESS read-only
			STATUS current
			DESCRIPTION
				"Description: "
			::= { tmdcStatistic 4 }

		
--     1.3.6.1.4.1.41475.3.1.4.2
-- 1.3.6.1.4.1.41475.3.1.4.2
-- 1.3.6.1.4.1.41475.3.1.3.5
-- 1.3.6.1.4.1.41475.3.1.3.5
		-- 1.3.6.1.4.1.41475.3.1.3.5
		tmdcLoadrate OBJECT-TYPE
			SYNTAX DisplayString
			UNITS "%"
			MAX-ACCESS read-only
			STATUS current
			DESCRIPTION
				"Description: "
			::= { tmdcStatistic 5 }

		
--     1.3.6.1.4.1.41475.3.1.4.2
-- 1.3.6.1.4.1.41475.3.1.4.2
-- 1.3.6.1.4.1.41475.3.1.3.5
-- 1.3.6.1.4.1.41475.3.1.3.6
		-- 1.3.6.1.4.1.41475.3.1.3.6
		tmdcEnergyAll OBJECT-TYPE
			SYNTAX DisplayString
			UNITS "kWh"
			MAX-ACCESS read-only
			STATUS current
			DESCRIPTION
				"Description: "
			::= { tmdcStatistic 6 }

		
--     1.3.6.1.4.1.41475.3.1.4.2
-- 1.3.6.1.4.1.41475.3.1.4.2
-- 1.3.6.1.4.1.41475.3.1.3.5
-- 1.3.6.1.4.1.41475.3.1.3.7
		-- 1.3.6.1.4.1.41475.3.1.3.7
		tmdcEnergyIT OBJECT-TYPE
			SYNTAX DisplayString
			UNITS "kWh"
			MAX-ACCESS read-only
			STATUS current
			DESCRIPTION
				"Description: "
			::= { tmdcStatistic 7 }

		
--     1.3.6.1.4.1.41475.3.1.5
-- 1.3.6.1.4.1.41475.3.1.5
-- 1.3.6.1.4.1.41475.3.1.4
-- 1.3.6.1.4.1.41475.3.1.4
		-- 1.3.6.1.4.1.41475.3.1.4
		tmdcMonObjects OBJECT IDENTIFIER ::= { tmdc 4 }

		
--     1.3.6.1.4.1.41475.3.1.5.2
-- 1.3.6.1.4.1.41475.3.1.5.2
-- 1.3.6.1.4.1.41475.3.1.4.1
-- 1.3.6.1.4.1.41475.3.1.4.1
		-- 1.3.6.1.4.1.41475.3.1.4.1
		main OBJECT IDENTIFIER ::= { tmdcMonObjects 1 }

		
--   1.3.6.1.4.1.41475.3.1.4.1.70
-- 1.3.6.1.4.1.41475.3.1.4.1.72
		-- 1.3.6.1.4.1.41475.3.1.4.1.1
		aVoltageLineAB OBJECT-TYPE
			SYNTAX DisplayString
			UNITS "V"
			MAX-ACCESS read-only
			STATUS current
			DESCRIPTION
				"Description: A, line AB voltage.
				"
			::= { main 1 }

		
--   1.3.6.1.4.1.41475.3.1.4.1.70
-- 1.3.6.1.4.1.41475.3.1.4.1.72
		-- 1.3.6.1.4.1.41475.3.1.4.1.2
		aVoltageLineBC OBJECT-TYPE
			SYNTAX DisplayString
			UNITS "V"
			MAX-ACCESS read-only
			STATUS current
			DESCRIPTION
				"Description: A, line BC voltage."
			::= { main 2 }

		
--   1.3.6.1.4.1.41475.3.1.4.1.70
-- 1.3.6.1.4.1.41475.3.1.4.1.72
		-- 1.3.6.1.4.1.41475.3.1.4.1.3
		aVoltageLineCA OBJECT-TYPE
			SYNTAX DisplayString
			UNITS "V"
			MAX-ACCESS read-only
			STATUS current
			DESCRIPTION
				"Description: A, line CA voltage."
			::= { main 3 }

		
--   1.3.6.1.4.1.41475.3.1.4.1.1
-- 1.3.6.1.4.1.41475.3.1.4.1.1
		-- 1.3.6.1.4.1.41475.3.1.4.1.4
		aVoltageA OBJECT-TYPE
			SYNTAX DisplayString
			UNITS "V"
			MAX-ACCESS read-only
			STATUS current
			DESCRIPTION
				"Description: A, A voltage."
			::= { main 4 }

		
--   1.3.6.1.4.1.41475.3.1.4.1.2
-- 1.3.6.1.4.1.41475.3.1.4.1.2
		-- 1.3.6.1.4.1.41475.3.1.4.1.5
		aVoltageB OBJECT-TYPE
			SYNTAX DisplayString
			UNITS "V"
			MAX-ACCESS read-only
			STATUS current
			DESCRIPTION
				"Description: A, B voltage."
			::= { main 5 }

		
--   1.3.6.1.4.1.41475.3.1.4.1.3
-- 1.3.6.1.4.1.41475.3.1.4.1.3
		-- 1.3.6.1.4.1.41475.3.1.4.1.6
		aVoltageC OBJECT-TYPE
			SYNTAX DisplayString
			UNITS "V"
			MAX-ACCESS read-only
			STATUS current
			DESCRIPTION
				"Description: A, C voltage."
			::= { main 6 }

		
--   1.3.6.1.4.1.41475.3.1.4.1.4
-- 1.3.6.1.4.1.41475.3.1.4.1.4
		-- 1.3.6.1.4.1.41475.3.1.4.1.7
		aCurrentA OBJECT-TYPE
			SYNTAX DisplayString
			UNITS "A"
			MAX-ACCESS read-only
			STATUS current
			DESCRIPTION
				"Description: A, A Current."
			::= { main 7 }

		
--   1.3.6.1.4.1.41475.3.1.4.1.5
-- 1.3.6.1.4.1.41475.3.1.4.1.5
		-- 1.3.6.1.4.1.41475.3.1.4.1.8
		aCurrentB OBJECT-TYPE
			SYNTAX DisplayString
			UNITS "A"
			MAX-ACCESS read-only
			STATUS current
			DESCRIPTION
				"Description: A, B Current."
			::= { main 8 }

		
--   1.3.6.1.4.1.41475.3.1.4.1.6
-- 1.3.6.1.4.1.41475.3.1.4.1.6
		-- 1.3.6.1.4.1.41475.3.1.4.1.9
		aCurrentC OBJECT-TYPE
			SYNTAX DisplayString
			UNITS "A"
			MAX-ACCESS read-only
			STATUS current
			DESCRIPTION
				"Description: A, C Current."
			::= { main 9 }

		
--   1.3.6.1.4.1.41475.3.1.4.1.7
-- 1.3.6.1.4.1.41475.3.1.4.1.7
		-- 1.3.6.1.4.1.41475.3.1.4.1.10
		aPowerFactorA OBJECT-TYPE
			SYNTAX DisplayString
			MAX-ACCESS read-only
			STATUS current
			DESCRIPTION
				"Description: A, A power factor.
				"
			::= { main 10 }

		
--   1.3.6.1.4.1.41475.3.1.4.1.8
-- 1.3.6.1.4.1.41475.3.1.4.1.8
		-- 1.3.6.1.4.1.41475.3.1.4.1.11
		aPowerFactorB OBJECT-TYPE
			SYNTAX DisplayString
			MAX-ACCESS read-only
			STATUS current
			DESCRIPTION
				"Description: A, B power factor."
			::= { main 11 }

		
--   1.3.6.1.4.1.41475.3.1.4.1.9
-- 1.3.6.1.4.1.41475.3.1.4.1.9
		-- 1.3.6.1.4.1.41475.3.1.4.1.12
		aPowerFactorC OBJECT-TYPE
			SYNTAX DisplayString
			MAX-ACCESS read-only
			STATUS current
			DESCRIPTION
				"Description: A, C power factor."
			::= { main 12 }

		
--   1.3.6.1.4.1.41475.3.1.4.1.10
-- 1.3.6.1.4.1.41475.3.1.4.1.10
		-- 1.3.6.1.4.1.41475.3.1.4.1.13
		aFrequency OBJECT-TYPE
			SYNTAX DisplayString
			UNITS "Hz"
			MAX-ACCESS read-only
			STATUS current
			DESCRIPTION
				"Description: A, Frequency."
			::= { main 13 }

		
--   1.3.6.1.4.1.41475.3.1.4.1.11
-- 1.3.6.1.4.1.41475.3.1.4.1.11
		-- 1.3.6.1.4.1.41475.3.1.4.1.14
		aActivePowerA OBJECT-TYPE
			SYNTAX DisplayString
			UNITS "kW"
			MAX-ACCESS read-only
			STATUS current
			DESCRIPTION
				"Description: A, A active power."
			::= { main 14 }

		
--   1.3.6.1.4.1.41475.3.1.4.1.12
-- 1.3.6.1.4.1.41475.3.1.4.1.12
		-- 1.3.6.1.4.1.41475.3.1.4.1.15
		aActivePowerB OBJECT-TYPE
			SYNTAX DisplayString
			UNITS "kW"
			MAX-ACCESS read-only
			STATUS current
			DESCRIPTION
				"Description: A, B active power."
			::= { main 15 }

		
--   1.3.6.1.4.1.41475.3.1.4.1.13
-- 1.3.6.1.4.1.41475.3.1.4.1.13
		-- 1.3.6.1.4.1.41475.3.1.4.1.16
		aActivePowerC OBJECT-TYPE
			SYNTAX DisplayString
			UNITS "kW"
			MAX-ACCESS read-only
			STATUS current
			DESCRIPTION
				"Description: A, C active power."
			::= { main 16 }

		
--   1.3.6.1.4.1.41475.3.1.4.1.14
-- 1.3.6.1.4.1.41475.3.1.4.1.14
		-- 1.3.6.1.4.1.41475.3.1.4.1.17
		aTotalActivePower OBJECT-TYPE
			SYNTAX DisplayString
			UNITS "kW"
			MAX-ACCESS read-only
			STATUS current
			DESCRIPTION
				"Description: A, total active power."
			::= { main 17 }

		
--   1.3.6.1.4.1.41475.3.1.4.1.15
-- 1.3.6.1.4.1.41475.3.1.4.1.15
		-- 1.3.6.1.4.1.41475.3.1.4.1.18
		aApparentPowerA OBJECT-TYPE
			SYNTAX DisplayString
			UNITS "kVA"
			MAX-ACCESS read-only
			STATUS current
			DESCRIPTION
				"Description: A, A apparent power."
			::= { main 18 }

		
--   1.3.6.1.4.1.41475.3.1.4.1.16
-- 1.3.6.1.4.1.41475.3.1.4.1.16
		-- 1.3.6.1.4.1.41475.3.1.4.1.19
		aApparentPowerB OBJECT-TYPE
			SYNTAX DisplayString
			UNITS "kVA"
			MAX-ACCESS read-only
			STATUS current
			DESCRIPTION
				"Description: A, B apparent power."
			::= { main 19 }

		
--   1.3.6.1.4.1.41475.3.1.4.1.17
-- 1.3.6.1.4.1.41475.3.1.4.1.17
		-- 1.3.6.1.4.1.41475.3.1.4.1.20
		aApparentPowerC OBJECT-TYPE
			SYNTAX DisplayString
			UNITS "kVA"
			MAX-ACCESS read-only
			STATUS current
			DESCRIPTION
				"Description: A, C apparent power."
			::= { main 20 }

		
--   1.3.6.1.4.1.41475.3.1.4.1.18
-- 1.3.6.1.4.1.41475.3.1.4.1.18
		-- 1.3.6.1.4.1.41475.3.1.4.1.21
		aTotalApparentPower OBJECT-TYPE
			SYNTAX DisplayString
			UNITS "kVA"
			MAX-ACCESS read-only
			STATUS current
			DESCRIPTION
				"Description: A, total apparent power."
			::= { main 21 }

		
--   1.3.6.1.4.1.41475.3.1.4.1.19
-- 1.3.6.1.4.1.41475.3.1.4.1.19
		-- 1.3.6.1.4.1.41475.3.1.4.1.22
		aEnergy OBJECT-TYPE
			SYNTAX DisplayString
			UNITS "kWh"
			MAX-ACCESS read-only
			STATUS current
			DESCRIPTION
				"Description: A, electrical degree."
			::= { main 22 }

		
--   1.3.6.1.4.1.41475.3.1.4.1.20
-- 1.3.6.1.4.1.41475.3.1.4.1.20
		-- 1.3.6.1.4.1.41475.3.1.4.1.23
		aNPEVoltage OBJECT-TYPE
			SYNTAX DisplayString
			UNITS "V"
			MAX-ACCESS read-only
			STATUS current
			DESCRIPTION
				"Description: A, N-PE Voltage."
			::= { main 23 }

		
--   1.3.6.1.4.1.41475.3.1.4.1.20
-- 1.3.6.1.4.1.41475.3.1.4.1.21
		-- 1.3.6.1.4.1.41475.3.1.4.1.24
		aZeroLineCurrent OBJECT-TYPE
			SYNTAX DisplayString
			UNITS "A"
			MAX-ACCESS read-only
			STATUS current
			DESCRIPTION
				"Description: A, Zero line current."
			::= { main 24 }

		
--   1.3.6.1.4.1.41475.3.1.4.1.21
-- 1.3.6.1.4.1.41475.3.1.4.1.22
		-- 1.3.6.1.4.1.41475.3.1.4.1.25
		aOvervoltage OBJECT-TYPE
			SYNTAX DisplayString
			MAX-ACCESS read-only
			STATUS current
			DESCRIPTION
				"Description: A, the state of overvoltage.
				Values: 0-ok, 1-alarm"
			::= { main 25 }

		
--   1.3.6.1.4.1.41475.3.1.4.1.22
-- 1.3.6.1.4.1.41475.3.1.4.1.23
		-- 1.3.6.1.4.1.41475.3.1.4.1.26
		aUndervoltage OBJECT-TYPE
			SYNTAX DisplayString
			MAX-ACCESS read-only
			STATUS current
			DESCRIPTION
				"Description: A, the state of undervoltage.
				Reasons: Below the undervoltage threshold, higher than the messing-phase boundary
				Values: 0-ok, 1-alarm"
			::= { main 26 }

		
--   1.3.6.1.4.1.41475.3.1.4.1.23
-- 1.3.6.1.4.1.41475.3.1.4.1.24
		-- 1.3.6.1.4.1.41475.3.1.4.1.27
		aMissingPhase OBJECT-TYPE
			SYNTAX DisplayString
			MAX-ACCESS read-only
			STATUS current
			DESCRIPTION
				"Description: A, the state of missing phase.
				Reasons: Any one phase voltage is lower than the messing-phase voltage.
				Values: 0-ok, 1-alarm"
			::= { main 27 }

		
--   1.3.6.1.4.1.41475.3.1.4.1.24
-- 1.3.6.1.4.1.41475.3.1.4.1.25
		-- 1.3.6.1.4.1.41475.3.1.4.1.28
		aOvercurrent OBJECT-TYPE
			SYNTAX DisplayString
			MAX-ACCESS read-only
			STATUS current
			DESCRIPTION
				"Description: A, the state of overcurrent.
				Reasons: Commercial power output current is greater than 1.25 times of the rated current
				Values: 0-ok, 1-alarm"
			::= { main 28 }

		
--   1.3.6.1.4.1.41475.3.1.4.1.26
-- 1.3.6.1.4.1.41475.3.1.4.1.27
		-- 1.3.6.1.4.1.41475.3.1.4.1.29
		aPowerCut OBJECT-TYPE
			SYNTAX DisplayString
			MAX-ACCESS read-only
			STATUS current
			DESCRIPTION
				"Description: A, the state of A power cut.
				Values: 0-ok, 1-alarm"
			::= { main 29 }

		
--   1.3.6.1.4.1.41475.3.1.4.1.27
-- 1.3.6.1.4.1.41475.3.1.4.1.28
		-- 1.3.6.1.4.1.41475.3.1.4.1.30
		aPowerInputCircuitBreaker OBJECT-TYPE
			SYNTAX DisplayString
			MAX-ACCESS read-only
			STATUS current
			DESCRIPTION
				"Description: A, the state of power input circuit breaker.
				Values: 0-ok, 1-open"
			::= { main 30 }

		
--   1.3.6.1.4.1.41475.3.1.4.1.70
-- 1.3.6.1.4.1.41475.3.1.4.1.72
		-- 1.3.6.1.4.1.41475.3.1.4.1.31
		bVoltageLineAB OBJECT-TYPE
			SYNTAX DisplayString
			UNITS "V"
			MAX-ACCESS read-only
			STATUS current
			DESCRIPTION
				"Description: B, line AB voltage."
			::= { main 31 }

		
--   1.3.6.1.4.1.41475.3.1.4.1.70
-- 1.3.6.1.4.1.41475.3.1.4.1.72
		-- 1.3.6.1.4.1.41475.3.1.4.1.32
		bVoltageLineBC OBJECT-TYPE
			SYNTAX DisplayString
			UNITS "V"
			MAX-ACCESS read-only
			STATUS current
			DESCRIPTION
				"Description: B, line BC voltage."
			::= { main 32 }

		
--   1.3.6.1.4.1.41475.3.1.4.1.70
-- 1.3.6.1.4.1.41475.3.1.4.1.72
		-- 1.3.6.1.4.1.41475.3.1.4.1.33
		bVoltageLineCA OBJECT-TYPE
			SYNTAX DisplayString
			UNITS "V"
			MAX-ACCESS read-only
			STATUS current
			DESCRIPTION
				"Description: B, line CA voltage."
			::= { main 33 }

		
--   1.3.6.1.4.1.41475.3.1.4.1.28
-- 1.3.6.1.4.1.41475.3.1.4.1.29
		-- 1.3.6.1.4.1.41475.3.1.4.1.34
		bVoltageA OBJECT-TYPE
			SYNTAX DisplayString
			UNITS "V"
			MAX-ACCESS read-only
			STATUS current
			DESCRIPTION
				"Description: B, A voltage."
			::= { main 34 }

		
--   1.3.6.1.4.1.41475.3.1.4.1.29
-- 1.3.6.1.4.1.41475.3.1.4.1.30
		-- 1.3.6.1.4.1.41475.3.1.4.1.35
		bVoltageB OBJECT-TYPE
			SYNTAX DisplayString
			UNITS "V"
			MAX-ACCESS read-only
			STATUS current
			DESCRIPTION
				"Description: B, B voltage."
			::= { main 35 }

		
--   1.3.6.1.4.1.41475.3.1.4.1.30
-- 1.3.6.1.4.1.41475.3.1.4.1.31
		-- 1.3.6.1.4.1.41475.3.1.4.1.36
		bVoltageC OBJECT-TYPE
			SYNTAX DisplayString
			UNITS "V"
			MAX-ACCESS read-only
			STATUS current
			DESCRIPTION
				"Description: B, C voltage."
			::= { main 36 }

		
--   1.3.6.1.4.1.41475.3.1.4.1.31
-- 1.3.6.1.4.1.41475.3.1.4.1.32
		-- 1.3.6.1.4.1.41475.3.1.4.1.37
		bCurrentA OBJECT-TYPE
			SYNTAX DisplayString
			UNITS "A"
			MAX-ACCESS read-only
			STATUS current
			DESCRIPTION
				"Description: B, A Current."
			::= { main 37 }

		
--   1.3.6.1.4.1.41475.3.1.4.1.32
-- 1.3.6.1.4.1.41475.3.1.4.1.33
		-- 1.3.6.1.4.1.41475.3.1.4.1.38
		bCurrentB OBJECT-TYPE
			SYNTAX DisplayString
			UNITS "A"
			MAX-ACCESS read-only
			STATUS current
			DESCRIPTION
				"Description: A, B Current."
			::= { main 38 }

		
--   1.3.6.1.4.1.41475.3.1.4.1.33
-- 1.3.6.1.4.1.41475.3.1.4.1.34
		-- 1.3.6.1.4.1.41475.3.1.4.1.39
		bCurrentC OBJECT-TYPE
			SYNTAX DisplayString
			UNITS "A"
			MAX-ACCESS read-only
			STATUS current
			DESCRIPTION
				"Description: B, C Current."
			::= { main 39 }

		
--   1.3.6.1.4.1.41475.3.1.4.1.34
-- 1.3.6.1.4.1.41475.3.1.4.1.35
		-- 1.3.6.1.4.1.41475.3.1.4.1.40
		bPowerFactorA OBJECT-TYPE
			SYNTAX DisplayString
			MAX-ACCESS read-only
			STATUS current
			DESCRIPTION
				"Description: B, A power factor."
			::= { main 40 }

		
--   1.3.6.1.4.1.41475.3.1.4.1.35
-- 1.3.6.1.4.1.41475.3.1.4.1.36
		-- 1.3.6.1.4.1.41475.3.1.4.1.41
		bPowerFactorB OBJECT-TYPE
			SYNTAX DisplayString
			MAX-ACCESS read-only
			STATUS current
			DESCRIPTION
				"Description: B, B power factor."
			::= { main 41 }

		
--   1.3.6.1.4.1.41475.3.1.4.1.36
-- 1.3.6.1.4.1.41475.3.1.4.1.37
		-- 1.3.6.1.4.1.41475.3.1.4.1.42
		bPowerFactorC OBJECT-TYPE
			SYNTAX DisplayString
			MAX-ACCESS read-only
			STATUS current
			DESCRIPTION
				"Description: B, C power factor."
			::= { main 42 }

		
--   1.3.6.1.4.1.41475.3.1.4.1.37
-- 1.3.6.1.4.1.41475.3.1.4.1.38
		-- 1.3.6.1.4.1.41475.3.1.4.1.43
		bFrequency OBJECT-TYPE
			SYNTAX DisplayString
			UNITS "Hz"
			MAX-ACCESS read-only
			STATUS current
			DESCRIPTION
				"Description: B, frequency."
			::= { main 43 }

		
--   1.3.6.1.4.1.41475.3.1.4.1.38
-- 1.3.6.1.4.1.41475.3.1.4.1.39
		-- 1.3.6.1.4.1.41475.3.1.4.1.44
		bActivePowerA OBJECT-TYPE
			SYNTAX DisplayString
			UNITS "kW"
			MAX-ACCESS read-only
			STATUS current
			DESCRIPTION
				"Description: B, A active power."
			::= { main 44 }

		
--   1.3.6.1.4.1.41475.3.1.4.1.39
-- 1.3.6.1.4.1.41475.3.1.4.1.40
		-- 1.3.6.1.4.1.41475.3.1.4.1.45
		bActivePowerB OBJECT-TYPE
			SYNTAX DisplayString
			UNITS "kW"
			MAX-ACCESS read-only
			STATUS current
			DESCRIPTION
				"Description: B, B active power."
			::= { main 45 }

		
--   1.3.6.1.4.1.41475.3.1.4.1.40
-- 1.3.6.1.4.1.41475.3.1.4.1.41
		-- 1.3.6.1.4.1.41475.3.1.4.1.46
		bActivePowerC OBJECT-TYPE
			SYNTAX DisplayString
			UNITS "kW"
			MAX-ACCESS read-only
			STATUS current
			DESCRIPTION
				"Description: B, C active power."
			::= { main 46 }

		
--   1.3.6.1.4.1.41475.3.1.4.1.41
-- 1.3.6.1.4.1.41475.3.1.4.1.42
		-- 1.3.6.1.4.1.41475.3.1.4.1.47
		bTotalActivePower OBJECT-TYPE
			SYNTAX DisplayString
			UNITS "kW"
			MAX-ACCESS read-only
			STATUS current
			DESCRIPTION
				"Description: B, total active power."
			::= { main 47 }

		
--   1.3.6.1.4.1.41475.3.1.4.1.42
-- 1.3.6.1.4.1.41475.3.1.4.1.43
		-- 1.3.6.1.4.1.41475.3.1.4.1.48
		bApparentPowerA OBJECT-TYPE
			SYNTAX DisplayString
			UNITS "kVA"
			MAX-ACCESS read-only
			STATUS current
			DESCRIPTION
				"Description: B, A apparent power."
			::= { main 48 }

		
--   1.3.6.1.4.1.41475.3.1.4.1.43
-- 1.3.6.1.4.1.41475.3.1.4.1.44
		-- 1.3.6.1.4.1.41475.3.1.4.1.49
		bApparentPowerB OBJECT-TYPE
			SYNTAX DisplayString
			UNITS "kVA"
			MAX-ACCESS read-only
			STATUS current
			DESCRIPTION
				"Description: B, B apparent power."
			::= { main 49 }

		
--   1.3.6.1.4.1.41475.3.1.4.1.44
-- 1.3.6.1.4.1.41475.3.1.4.1.45
		-- 1.3.6.1.4.1.41475.3.1.4.1.50
		bApparentPowerC OBJECT-TYPE
			SYNTAX DisplayString
			UNITS "kVA"
			MAX-ACCESS read-only
			STATUS current
			DESCRIPTION
				"Description: B, C apparent power."
			::= { main 50 }

		
--   1.3.6.1.4.1.41475.3.1.4.1.45
-- 1.3.6.1.4.1.41475.3.1.4.1.46
		-- 1.3.6.1.4.1.41475.3.1.4.1.51
		bTotalApparentPower OBJECT-TYPE
			SYNTAX DisplayString
			UNITS "kVA"
			MAX-ACCESS read-only
			STATUS current
			DESCRIPTION
				"Description: B, total apparent power."
			::= { main 51 }

		
--   1.3.6.1.4.1.41475.3.1.4.1.46
-- 1.3.6.1.4.1.41475.3.1.4.1.47
		-- 1.3.6.1.4.1.41475.3.1.4.1.52
		bEnergy OBJECT-TYPE
			SYNTAX DisplayString
			UNITS "kWh"
			MAX-ACCESS read-only
			STATUS current
			DESCRIPTION
				"Description: B, electrical degree."
			::= { main 52 }

		
--   1.3.6.1.4.1.41475.3.1.4.1.47
-- 1.3.6.1.4.1.41475.3.1.4.1.48
		-- 1.3.6.1.4.1.41475.3.1.4.1.53
		bNPEVoltage OBJECT-TYPE
			SYNTAX DisplayString
			UNITS "V"
			MAX-ACCESS read-only
			STATUS current
			DESCRIPTION
				"Description: B, N-PE Voltage."
			::= { main 53 }

		
--   1.3.6.1.4.1.41475.3.1.4.1.20
-- 1.3.6.1.4.1.41475.3.1.4.1.49
		-- 1.3.6.1.4.1.41475.3.1.4.1.54
		bZeroLineCurrent OBJECT-TYPE
			SYNTAX DisplayString
			UNITS "A"
			MAX-ACCESS read-only
			STATUS current
			DESCRIPTION
				"Description: B, Zero line current."
			::= { main 54 }

		
--   1.3.6.1.4.1.41475.3.1.4.1.48
-- 1.3.6.1.4.1.41475.3.1.4.1.50
		-- 1.3.6.1.4.1.41475.3.1.4.1.55
		bOvervoltage OBJECT-TYPE
			SYNTAX DisplayString
			MAX-ACCESS read-only
			STATUS current
			DESCRIPTION
				"Description: B, the state of overvoltage.
				Values: 0-ok, 1-alarm"
			::= { main 55 }

		
--   1.3.6.1.4.1.41475.3.1.4.1.49
-- 1.3.6.1.4.1.41475.3.1.4.1.51
		-- 1.3.6.1.4.1.41475.3.1.4.1.56
		bUndervoltage OBJECT-TYPE
			SYNTAX DisplayString
			MAX-ACCESS read-only
			STATUS current
			DESCRIPTION
				"Description: B, the state of undervoltage.
				Reasons: Below the undervoltage threshold, higher than the messing-phase boundary
				Values: 0-ok, 1-alarm"
			::= { main 56 }

		
--   1.3.6.1.4.1.41475.3.1.4.1.50
-- 1.3.6.1.4.1.41475.3.1.4.1.52
		-- 1.3.6.1.4.1.41475.3.1.4.1.57
		bMissingPhase OBJECT-TYPE
			SYNTAX DisplayString
			MAX-ACCESS read-only
			STATUS current
			DESCRIPTION
				"Description: B, the state of missing phase.
				Reasons: Any one phase voltage is lower than the messing-phase voltage.
				Values: 0-ok, 1-alarm
				
				"
			::= { main 57 }

		
--   1.3.6.1.4.1.41475.3.1.4.1.51
-- 1.3.6.1.4.1.41475.3.1.4.1.53
		-- 1.3.6.1.4.1.41475.3.1.4.1.58
		bOvercurrent OBJECT-TYPE
			SYNTAX DisplayString
			MAX-ACCESS read-only
			STATUS current
			DESCRIPTION
				"Description: B, the state of overcurrent.
				Reasons: Commercial power output current is greater than 1.25 times of the rated current
				Values: 0-ok, 1-alarm"
			::= { main 58 }

		
--   1.3.6.1.4.1.41475.3.1.4.1.53
-- 1.3.6.1.4.1.41475.3.1.4.1.55
		-- 1.3.6.1.4.1.41475.3.1.4.1.59
		bPowerCut OBJECT-TYPE
			SYNTAX DisplayString
			MAX-ACCESS read-only
			STATUS current
			DESCRIPTION
				"Description: B, the state of A power cut.
				Values: 0-ok, 1-alarm"
			::= { main 59 }

		
--   1.3.6.1.4.1.41475.3.1.4.1.54
-- 1.3.6.1.4.1.41475.3.1.4.1.56
		-- 1.3.6.1.4.1.41475.3.1.4.1.60
		bPowerInputCircuitBreaker OBJECT-TYPE
			SYNTAX DisplayString
			MAX-ACCESS read-only
			STATUS current
			DESCRIPTION
				"Description: B, the state of power input circuit breaker.
				Values: 0-ok, 1-open"
			::= { main 60 }

		
--   1.3.6.1.4.1.41475.3.1.4.1.25
-- 1.3.6.1.4.1.41475.3.1.4.1.26
		-- 1.3.6.1.4.1.41475.3.1.4.1.61
		atsInputCircuitBreakerA OBJECT-TYPE
			SYNTAX DisplayString
			MAX-ACCESS read-only
			STATUS current
			DESCRIPTION
				"Description: A, the state of ATS input circuit breaker.
				Values: 0-ok, 1-open"
			::= { main 61 }

		
--   1.3.6.1.4.1.41475.3.1.4.1.52
-- 1.3.6.1.4.1.41475.3.1.4.1.54
		-- 1.3.6.1.4.1.41475.3.1.4.1.62
		atsInputCircuitBreakerB OBJECT-TYPE
			SYNTAX DisplayString
			MAX-ACCESS read-only
			STATUS current
			DESCRIPTION
				"Description: B, the state of ATS input circuit breaker.
				Values: 0-ok, 1-open"
			::= { main 62 }

		
--   1.3.6.1.4.1.41475.3.1.4.1.61
-- 1.3.6.1.4.1.41475.3.1.4.1.63
		-- 1.3.6.1.4.1.41475.3.1.4.1.63
		atsStandbySwitch OBJECT-TYPE
			SYNTAX DisplayString
			MAX-ACCESS read-only
			STATUS current
			DESCRIPTION
				"Description: the state of standby switch.
				Values: 0-open, 1-close"
			::= { main 63 }

		
--   1.3.6.1.4.1.41475.3.1.4.1.62
-- 1.3.6.1.4.1.41475.3.1.4.1.64
		-- 1.3.6.1.4.1.41475.3.1.4.1.64
		atsCommonSwitch OBJECT-TYPE
			SYNTAX DisplayString
			MAX-ACCESS read-only
			STATUS current
			DESCRIPTION
				"Description: the state of common switch.
				Values: 0-open, 1-close"
			::= { main 64 }

		
--   1.3.6.1.4.1.41475.3.1.4.1.63
-- 1.3.6.1.4.1.41475.3.1.4.1.65
		-- 1.3.6.1.4.1.41475.3.1.4.1.65
		atsControlMode OBJECT-TYPE
			SYNTAX DisplayString
			MAX-ACCESS read-only
			STATUS current
			DESCRIPTION
				"Description: Manual, automatic control mode.
				Values: 0-automatic, 1-manual"
			::= { main 65 }

		
--   1.3.6.1.4.1.41475.3.1.4.1.64
-- 1.3.6.1.4.1.41475.3.1.4.1.66
		-- 1.3.6.1.4.1.41475.3.1.4.1.66
		atsFaultCauseLocking OBJECT-TYPE
			SYNTAX DisplayString
			MAX-ACCESS read-only
			STATUS current
			DESCRIPTION
				"Description: Some fault causes the switch locking.
				Values: 0-ok, 1-alarm"
			::= { main 66 }

		
--   1.3.6.1.4.1.41475.3.1.4.1.68
-- 1.3.6.1.4.1.41475.3.1.4.1.70
		-- 1.3.6.1.4.1.41475.3.1.4.1.67
		acSensorFault OBJECT-TYPE
			SYNTAX DisplayString
			MAX-ACCESS read-only
			STATUS current
			DESCRIPTION
				"Description: AC sensor or controler fault.
				Values: 0-ok, 1-alarm"
			::= { main 67 }

		
--   1.3.6.1.4.1.41475.3.1.4.1.69
-- 1.3.6.1.4.1.41475.3.1.4.1.71
		-- 1.3.6.1.4.1.41475.3.1.4.1.68
		dcSensorFault OBJECT-TYPE
			SYNTAX DisplayString
			MAX-ACCESS read-only
			STATUS current
			DESCRIPTION
				"Description: DC sensor or controler fault.
				Values: 0-ok, 1-alarm"
			::= { main 68 }

		
--   1.3.6.1.4.1.41475.3.1.4.1.70
-- 1.3.6.1.4.1.41475.3.1.4.1.72
		-- 1.3.6.1.4.1.41475.3.1.4.1.69
		insulationSensorFault OBJECT-TYPE
			SYNTAX DisplayString
			MAX-ACCESS read-only
			STATUS current
			DESCRIPTION
				"Description: Insulation sensor or controler fault
				Values: 0-ok, 1-alarm"
			::= { main 69 }

		
--   1.3.6.1.4.1.41475.3.1.4.1.68
-- 1.3.6.1.4.1.41475.3.1.4.1.70
		-- 1.3.6.1.4.1.41475.3.1.4.1.70
		spdTvssBreakerStatus OBJECT-TYPE
			SYNTAX DisplayString
			MAX-ACCESS read-only
			STATUS current
			DESCRIPTION
				"Description: SPD or TVSS or break fault.
				Values: 0-ok, 1-fault."
			::= { main 70 }

		
--   1.3.6.1.4.1.41475.3.1.4.1.70
-- 1.3.6.1.4.1.41475.3.1.4.1.72
		-- 1.3.6.1.4.1.41475.3.1.4.1.71
		acOutputTotalCurrent OBJECT-TYPE
			SYNTAX DisplayString
			UNITS "A"
			MAX-ACCESS read-only
			STATUS current
			DESCRIPTION
				"Description: The AC total current."
			::= { main 71 }

		
--   1.3.6.1.4.1.41475.3.1.4.1.70
-- 1.3.6.1.4.1.41475.3.1.4.1.72
		-- 1.3.6.1.4.1.41475.3.1.4.1.72
		acOutputITCurrent OBJECT-TYPE
			SYNTAX DisplayString
			UNITS "A"
			MAX-ACCESS read-only
			STATUS current
			DESCRIPTION
				"Description: The AC IT current."
			::= { main 72 }

		
--   1.3.6.1.4.1.41475.3.1.4.1.70
-- 1.3.6.1.4.1.41475.3.1.4.1.72
		-- 1.3.6.1.4.1.41475.3.1.4.1.73
		acOutputTotalPower OBJECT-TYPE
			SYNTAX DisplayString
			UNITS "kW"
			MAX-ACCESS read-only
			STATUS current
			DESCRIPTION
				"Description: The AC total power."
			::= { main 73 }

		
--   1.3.6.1.4.1.41475.3.1.4.1.70
-- 1.3.6.1.4.1.41475.3.1.4.1.72
		-- 1.3.6.1.4.1.41475.3.1.4.1.74
		acOutputITPower OBJECT-TYPE
			SYNTAX DisplayString
			UNITS "kW"
			MAX-ACCESS read-only
			STATUS current
			DESCRIPTION
				"Description: The AC IT power."
			::= { main 74 }

		
--   1.3.6.1.4.1.41475.3.1.4.1.70
-- 1.3.6.1.4.1.41475.3.1.4.1.72
		-- 1.3.6.1.4.1.41475.3.1.4.1.75
		acOutputTotalEnergy OBJECT-TYPE
			SYNTAX DisplayString
			UNITS "kWh"
			MAX-ACCESS read-only
			STATUS current
			DESCRIPTION
				"Description: The AC total energy."
			::= { main 75 }

		
--   1.3.6.1.4.1.41475.3.1.4.1.70
-- 1.3.6.1.4.1.41475.3.1.4.1.72
		-- 1.3.6.1.4.1.41475.3.1.4.1.76
		acOutputITEnergy OBJECT-TYPE
			SYNTAX DisplayString
			UNITS "kWh"
			MAX-ACCESS read-only
			STATUS current
			DESCRIPTION
				"Description: The AC IT energy."
			::= { main 76 }

		
--   1.3.6.1.4.1.41475.3.1.4.1.70
-- 1.3.6.1.4.1.41475.3.1.4.1.72
		-- 1.3.6.1.4.1.41475.3.1.4.1.77
		dcOutputTotalCurrent OBJECT-TYPE
			SYNTAX DisplayString
			UNITS "A"
			MAX-ACCESS read-only
			STATUS current
			DESCRIPTION
				"Description: The AC total current."
			::= { main 77 }

		
--   1.3.6.1.4.1.41475.3.1.4.1.70
-- 1.3.6.1.4.1.41475.3.1.4.1.72
		-- 1.3.6.1.4.1.41475.3.1.4.1.78
		dcOutputITCurrent OBJECT-TYPE
			SYNTAX DisplayString
			UNITS "A"
			MAX-ACCESS read-only
			STATUS current
			DESCRIPTION
				"Description: The AC IT current."
			::= { main 78 }

		
--   1.3.6.1.4.1.41475.3.1.4.1.70
-- 1.3.6.1.4.1.41475.3.1.4.1.72
		-- 1.3.6.1.4.1.41475.3.1.4.1.79
		dcOutputTotalPower OBJECT-TYPE
			SYNTAX DisplayString
			UNITS "kW"
			MAX-ACCESS read-only
			STATUS current
			DESCRIPTION
				"Description: The AC total power."
			::= { main 79 }

		
--   1.3.6.1.4.1.41475.3.1.4.1.70
-- 1.3.6.1.4.1.41475.3.1.4.1.72
		-- 1.3.6.1.4.1.41475.3.1.4.1.80
		dcOutputITPower OBJECT-TYPE
			SYNTAX DisplayString
			UNITS "kW"
			MAX-ACCESS read-only
			STATUS current
			DESCRIPTION
				"Description: The AC IT power."
			::= { main 80 }

		
--   1.3.6.1.4.1.41475.3.1.4.1.70
-- 1.3.6.1.4.1.41475.3.1.4.1.72
		-- 1.3.6.1.4.1.41475.3.1.4.1.81
		dcOutputTotalEnergy OBJECT-TYPE
			SYNTAX DisplayString
			UNITS "kWh"
			MAX-ACCESS read-only
			STATUS current
			DESCRIPTION
				"Description: The AC total energy."
			::= { main 81 }

		
--   1.3.6.1.4.1.41475.3.1.4.1.70
-- 1.3.6.1.4.1.41475.3.1.4.1.72
		-- 1.3.6.1.4.1.41475.3.1.4.1.82
		dcOutputITEnergy OBJECT-TYPE
			SYNTAX DisplayString
			UNITS "kWh"
			MAX-ACCESS read-only
			STATUS current
			DESCRIPTION
				"Description: The AC IT energy."
			::= { main 82 }

		
--     1.3.6.1.4.1.41475.3.1.5.3
-- 1.3.6.1.4.1.41475.3.1.5.3
-- 1.3.6.1.4.1.41475.3.1.4.2
-- 1.3.6.1.4.1.41475.3.1.4.2
		-- 1.3.6.1.4.1.41475.3.1.4.2
		hvdc OBJECT IDENTIFIER ::= { tmdcMonObjects 2 }

		
		-- 1.3.6.1.4.1.41475.3.1.4.2.1
		hvdcSystemTable OBJECT-TYPE
			SYNTAX SEQUENCE OF HvdcSystemEntry
			MAX-ACCESS not-accessible
			STATUS current
			DESCRIPTION
				"Description."
			::= { hvdc 1 }

		
		-- 1.3.6.1.4.1.41475.3.1.4.2.1.1
		hvdcSystemEntry OBJECT-TYPE
			SYNTAX HvdcSystemEntry
			MAX-ACCESS not-accessible
			STATUS current
			DESCRIPTION
				"Description."
			INDEX { hvdcSystemIndex }
			::= { hvdcSystemTable 1 }

		
		HvdcSystemEntry ::=
			SEQUENCE { 
				hvdcSystemIndex
					Integer32,
				hvdcOutputVoltage
					DisplayString,
				hvdcPositiveVoltageToGround
					DisplayString,
				hvdcNegativeVoltageToGround
					DisplayString,
				hvdcOutputTotalCurrent
					DisplayString,
				hvdcOutputITCurrent
					DisplayString,
				hvdcOutputTotalPower
					DisplayString,
				hvdcOutputITPower
					DisplayString,
				hvdcModuleCount
					DisplayString,
				hvdcModuleMaxPower
					DisplayString,
				hvdcPositiveInsulationFault
					DisplayString,
				hvdcNegativeInsulationFault
					DisplayString,
				hvdcOutputCircuitBreaker
					DisplayString,
				hvdcAlarmStatus
					DisplayString
			 }

--     1.3.6.1.4.1.41475.3.1.5.3.1.1.1
-- 1.3.6.1.4.1.41475.3.1.5.3.1.1.1
-- 1.3.6.1.4.1.41475.3.1.4.2.1.1.1
-- 1.3.6.1.4.1.41475.3.1.4.2.1.1.1
		-- 1.3.6.1.4.1.41475.3.1.4.2.1.1.1
		hvdcSystemIndex OBJECT-TYPE
			SYNTAX Integer32 (1..9999)
			MAX-ACCESS read-only
			STATUS current
			DESCRIPTION
				"Description: The serial number, starting from 1"
			::= { hvdcSystemEntry 1 }

		
		-- 1.3.6.1.4.1.41475.3.1.4.2.1.1.2
		hvdcOutputVoltage OBJECT-TYPE
			SYNTAX DisplayString
			UNITS "V"
			MAX-ACCESS read-only
			STATUS current
			DESCRIPTION
				"Description: The hvdc output voltage."
			::= { hvdcSystemEntry 2 }

		
		-- 1.3.6.1.4.1.41475.3.1.4.2.1.1.3
		hvdcPositiveVoltageToGround OBJECT-TYPE
			SYNTAX DisplayString
			UNITS "V"
			MAX-ACCESS read-only
			STATUS current
			DESCRIPTION
				"Description: The hvdc voltage of positive to the ground"
			::= { hvdcSystemEntry 3 }

		
		-- 1.3.6.1.4.1.41475.3.1.4.2.1.1.4
		hvdcNegativeVoltageToGround OBJECT-TYPE
			SYNTAX DisplayString
			UNITS "V"
			MAX-ACCESS read-only
			STATUS current
			DESCRIPTION
				"Description: The hvdc voltage of negative to the ground"
			::= { hvdcSystemEntry 4 }

		
		-- 1.3.6.1.4.1.41475.3.1.4.2.1.1.5
		hvdcOutputTotalCurrent OBJECT-TYPE
			SYNTAX DisplayString
			UNITS "A"
			MAX-ACCESS read-only
			STATUS current
			DESCRIPTION
				"Description: the hvdc total current."
			::= { hvdcSystemEntry 5 }

		
		-- 1.3.6.1.4.1.41475.3.1.4.2.1.1.6
		hvdcOutputITCurrent OBJECT-TYPE
			SYNTAX DisplayString
			UNITS "A"
			MAX-ACCESS read-only
			STATUS current
			DESCRIPTION
				"Description: the hvdc it current."
			::= { hvdcSystemEntry 6 }

		
		-- 1.3.6.1.4.1.41475.3.1.4.2.1.1.7
		hvdcOutputTotalPower OBJECT-TYPE
			SYNTAX DisplayString
			UNITS "kW"
			MAX-ACCESS read-only
			STATUS current
			DESCRIPTION
				"Description: the hvdc total power."
			::= { hvdcSystemEntry 7 }

		
		-- 1.3.6.1.4.1.41475.3.1.4.2.1.1.8
		hvdcOutputITPower OBJECT-TYPE
			SYNTAX DisplayString
			UNITS "kW"
			MAX-ACCESS read-only
			STATUS current
			DESCRIPTION
				"Description: the hvdc it power."
			::= { hvdcSystemEntry 8 }

		
		-- 1.3.6.1.4.1.41475.3.1.4.2.1.1.9
		hvdcModuleCount OBJECT-TYPE
			SYNTAX DisplayString
			MAX-ACCESS read-only
			STATUS current
			DESCRIPTION
				"Description: total count of rectifier module."
			::= { hvdcSystemEntry 9 }

		
		-- 1.3.6.1.4.1.41475.3.1.4.2.1.1.10
		hvdcModuleMaxPower OBJECT-TYPE
			SYNTAX DisplayString
			UNITS "kW"
			MAX-ACCESS read-only
			STATUS current
			DESCRIPTION			" "
			::= { hvdcSystemEntry 10 }

		
		-- 1.3.6.1.4.1.41475.3.1.4.2.1.1.11
		hvdcPositiveInsulationFault OBJECT-TYPE
			SYNTAX DisplayString
			MAX-ACCESS read-only
			STATUS current
			DESCRIPTION
				"Description: hvdc positive insulation fault.
				Values: 0-ok, 1-fault."
			::= { hvdcSystemEntry 11 }

		
		-- 1.3.6.1.4.1.41475.3.1.4.2.1.1.12
		hvdcNegativeInsulationFault OBJECT-TYPE
			SYNTAX DisplayString
			MAX-ACCESS read-only
			STATUS current
			DESCRIPTION
				"Description: hvdc negative insulation fault.
				Values: 0-ok, 1-fault."
			::= { hvdcSystemEntry 12 }

		
		-- 1.3.6.1.4.1.41475.3.1.4.2.1.1.13
		hvdcOutputCircuitBreaker OBJECT-TYPE
			SYNTAX DisplayString
			MAX-ACCESS read-only
			STATUS current
			DESCRIPTION
				"Description: alarm status of the HVDC
				Values: 0-ok, 1-alarm."
			::= { hvdcSystemEntry 13 }

		
		-- 1.3.6.1.4.1.41475.3.1.4.2.1.1.14
		hvdcAlarmStatus OBJECT-TYPE
			SYNTAX DisplayString
			UNITS "kW"
			MAX-ACCESS read-only
			STATUS current
			DESCRIPTION
				"Description: alarm status of the HVDC
				Values: 0-ok, 1-alarm."
			::= { hvdcSystemEntry 14 }

		
--     1.3.6.1.4.1.41475.3.1.5.3.1
-- 1.3.6.1.4.1.41475.3.1.5.3.1
-- 1.3.6.1.4.1.41475.3.1.4.2.1
-- 1.3.6.1.4.1.41475.3.1.4.2.1
		-- 1.3.6.1.4.1.41475.3.1.4.2.2
		hvdcModuleTable OBJECT-TYPE
			SYNTAX SEQUENCE OF HvdcModuleEntry
			MAX-ACCESS not-accessible
			STATUS current
			DESCRIPTION
				"Description."
			::= { hvdc 2 }

		
--     1.3.6.1.4.1.41475.3.1.5.3.1.1
-- 1.3.6.1.4.1.41475.3.1.5.3.1.1
-- 1.3.6.1.4.1.41475.3.1.4.2.1.1
-- 1.3.6.1.4.1.41475.3.1.4.2.1.1
		-- 1.3.6.1.4.1.41475.3.1.4.2.2.1
		hvdcModuleEntry OBJECT-TYPE
			SYNTAX HvdcModuleEntry
			MAX-ACCESS not-accessible
			STATUS current
			DESCRIPTION
				"Description."
			INDEX { hvdcIndex }
			::= { hvdcModuleTable 1 }

		
		HvdcModuleEntry ::=
			SEQUENCE { 
				hvdcIndex
					Integer32,
				hvdcCurrent
					DisplayString,
				hvdcPower
					DisplayString,
				hvdcWorkingState
					DisplayString,
				hvdcOverTemperature
					DisplayString,
				hvdcFlowEqualize
					DisplayString
			 }

--     1.3.6.1.4.1.41475.3.1.5.3.1.1.1
-- 1.3.6.1.4.1.41475.3.1.5.3.1.1.1
-- 1.3.6.1.4.1.41475.3.1.4.2.1.1.1
-- 1.3.6.1.4.1.41475.3.1.4.2.1.1.1
		-- 1.3.6.1.4.1.41475.3.1.4.2.2.1.1
		hvdcIndex OBJECT-TYPE
			SYNTAX Integer32 (1..9999)
			MAX-ACCESS read-only
			STATUS current
			DESCRIPTION
				"Description: The serial number, starting from 1"
			::= { hvdcModuleEntry 1 }

		
--     1.3.6.1.4.1.41475.3.1.5.3.1.1.2
-- 1.3.6.1.4.1.41475.3.1.5.3.1.1.2
-- 1.3.6.1.4.1.41475.3.1.4.2.1.1.2
-- 1.3.6.1.4.1.41475.3.1.4.2.1.1.2
		-- 1.3.6.1.4.1.41475.3.1.4.2.2.1.2
		hvdcCurrent OBJECT-TYPE
			SYNTAX DisplayString
			UNITS "A"
			MAX-ACCESS read-only
			STATUS current
			DESCRIPTION
				"Description: Power"
			::= { hvdcModuleEntry 2 }

		
--     1.3.6.1.4.1.41475.3.1.5.3.1.1.2
-- 1.3.6.1.4.1.41475.3.1.5.3.1.1.2
-- 1.3.6.1.4.1.41475.3.1.4.2.1.1.2
-- 1.3.6.1.4.1.41475.3.1.4.2.1.1.2
		-- 1.3.6.1.4.1.41475.3.1.4.2.2.1.3
		hvdcPower OBJECT-TYPE
			SYNTAX DisplayString
			UNITS "kW"
			MAX-ACCESS read-only
			STATUS current
			DESCRIPTION
				"Description: Power"
			::= { hvdcModuleEntry 3 }

		
--     1.3.6.1.4.1.41475.3.1.5.3.1.1.3
-- 1.3.6.1.4.1.41475.3.1.5.3.1.1.3
-- 1.3.6.1.4.1.41475.3.1.4.2.1.1.3
-- 1.3.6.1.4.1.41475.3.1.4.2.1.1.3
		-- 1.3.6.1.4.1.41475.3.1.4.2.2.1.4
		hvdcWorkingState OBJECT-TYPE
			SYNTAX DisplayString
			MAX-ACCESS read-only
			STATUS current
			DESCRIPTION
				"Description: working state
				Values: 0-ok, 1-sleep."
			::= { hvdcModuleEntry 4 }

		
--     1.3.6.1.4.1.41475.3.1.5.3.1.1.4
-- 1.3.6.1.4.1.41475.3.1.5.3.1.1.4
-- 1.3.6.1.4.1.41475.3.1.4.2.1.1.5
-- 1.3.6.1.4.1.41475.3.1.4.2.1.1.5
		-- 1.3.6.1.4.1.41475.3.1.4.2.2.1.5
		hvdcOverTemperature OBJECT-TYPE
			SYNTAX DisplayString
			MAX-ACCESS read-only
			STATUS current
			DESCRIPTION
				"Description: over temperature.
				Values: 0-ok, 1-alarm."
			::= { hvdcModuleEntry 5 }

		
--     1.3.6.1.4.1.41475.3.1.5.3.1.1.4
-- 1.3.6.1.4.1.41475.3.1.5.3.1.1.4
-- 1.3.6.1.4.1.41475.3.1.4.2.1.1.8
-- 1.3.6.1.4.1.41475.3.1.4.2.1.1.8
		-- 1.3.6.1.4.1.41475.3.1.4.2.2.1.6
		hvdcFlowEqualize OBJECT-TYPE
			SYNTAX DisplayString
			MAX-ACCESS read-only
			STATUS current
			DESCRIPTION
				"Description: flow equalize fault.
				Values: 0-ok, 1-fault"
			::= { hvdcModuleEntry 6 }

		
--     1.3.6.1.4.1.41475.3.1.5.4
-- 1.3.6.1.4.1.41475.3.1.5.4
-- 1.3.6.1.4.1.41475.3.1.4.3
-- 1.3.6.1.4.1.41475.3.1.4.3
		-- 1.3.6.1.4.1.41475.3.1.4.3
		batLogging OBJECT IDENTIFIER ::= { tmdcMonObjects 3 }

		
--     1.3.6.1.4.1.41475.3.1.5.4.2
-- 1.3.6.1.4.1.41475.3.1.5.4.2
-- 1.3.6.1.4.1.41475.3.1.4.3.2
-- 1.3.6.1.4.1.41475.3.1.4.3.2
		-- 1.3.6.1.4.1.41475.3.1.4.3.1
		batGroupCapacity OBJECT-TYPE
			SYNTAX DisplayString
			UNITS "%"
			MAX-ACCESS read-only
			STATUS current
			DESCRIPTION
				"Description: Battery group capacity."
			::= { batLogging 1 }

		
--     1.3.6.1.4.1.41475.3.1.5.4.3
-- 1.3.6.1.4.1.41475.3.1.5.4.3
-- 1.3.6.1.4.1.41475.3.1.4.3.3
-- 1.3.6.1.4.1.41475.3.1.4.3.3
		-- 1.3.6.1.4.1.41475.3.1.4.3.2
		batGroupRemainingTime OBJECT-TYPE
			SYNTAX DisplayString
			UNITS "min"
			MAX-ACCESS read-only
			STATUS current
			DESCRIPTION
				"Description: The remaining time."
			::= { batLogging 2 }

		
--     1.3.6.1.4.1.41475.3.1.5.4.5
-- 1.3.6.1.4.1.41475.3.1.5.4.5
-- 1.3.6.1.4.1.41475.3.1.4.3.17
-- 1.3.6.1.4.1.41475.3.1.4.3.17
		-- 1.3.6.1.4.1.41475.3.1.4.3.3
		batBatteryTesterFault OBJECT-TYPE
			SYNTAX DisplayString
			MAX-ACCESS read-only
			STATUS current
			DESCRIPTION
				"Description: The battery tester status
				Values: 0-ok, 1-fault"
			::= { batLogging 3 }

		
--     1.3.6.1.4.1.41475.3.1.5.4.9
-- 1.3.6.1.4.1.41475.3.1.5.4.9
-- 1.3.6.1.4.1.41475.3.1.4.3.18
-- 1.3.6.1.4.1.41475.3.1.4.3.18
		-- 1.3.6.1.4.1.41475.3.1.4.3.4
		batGroupTable OBJECT-TYPE
			SYNTAX SEQUENCE OF BatGroupEntry
			MAX-ACCESS not-accessible
			STATUS current
			DESCRIPTION
				"Description."
			::= { batLogging 4 }

		
--     1.3.6.1.4.1.41475.3.1.5.4.9.1
-- 1.3.6.1.4.1.41475.3.1.5.4.9.1
-- 1.3.6.1.4.1.41475.3.1.4.3.18.1
-- 1.3.6.1.4.1.41475.3.1.4.3.18.1
		-- 1.3.6.1.4.1.41475.3.1.4.3.4.1
		batGroupEntry OBJECT-TYPE
			SYNTAX BatGroupEntry
			MAX-ACCESS not-accessible
			STATUS current
			DESCRIPTION
				"Description."
			INDEX { batGroupIndex }
			::= { batGroupTable 1 }

		
		BatGroupEntry ::=
			SEQUENCE { 
				batGroupIndex
					Integer32,
				batGroupVolt
					DisplayString,
				batGroupCurrent
					DisplayString,
				batGroupChargeCurrentH
					DisplayString,
				batGroupDischargeCurrentH
					DisplayString,
				batGroupBreakerStatus
					DisplayString,
				batGroupPositiveFuseStatus
					DisplayString,
				batGroupNegativeFuseStatus
					DisplayString,
				batGroupVoltUneven
					DisplayString,
				batGroupResistanceUneven
					DisplayString,
				batGroupCell1Volt
					DisplayString,
				batGroupCell1Resistance
					DisplayString,
				batGroupCell1Temp
					DisplayString,
				batGroupCell2Volt
					DisplayString,
				batGroupCell2Resistance
					DisplayString,
				batGroupCell2Temp
					DisplayString,
				batGroupCell3Volt
					DisplayString,
				batGroupCell3Resistance
					DisplayString,
				batGroupCell3Temp
					DisplayString,
				batGroupCell4Volt
					DisplayString,
				batGroupCell4Resistance
					DisplayString,
				batGroupCell4Temp
					DisplayString,
				batGroupCell5Volt
					DisplayString,
				batGroupCell5Resistance
					DisplayString,
				batGroupCell5Temp
					DisplayString,
				batGroupCell6Volt
					DisplayString,
				batGroupCell6Resistance
					DisplayString,
				batGroupCell6Temp
					DisplayString,
				batGroupCell7Volt
					DisplayString,
				batGroupCell7Resistance
					DisplayString,
				batGroupCell7Temp
					DisplayString,
				batGroupCell8Volt
					DisplayString,
				batGroupCell8Resistance
					DisplayString,
				batGroupCell8Temp
					DisplayString,
				batGroupCell9Volt
					DisplayString,
				batGroupCell9Resistance
					DisplayString,
				batGroupCell9Temp
					DisplayString,
				batGroupCell10Volt
					DisplayString,
				batGroupCell10Resistance
					DisplayString,
				batGroupCell10Temp
					DisplayString,
				batGroupCell11Volt
					DisplayString,
				batGroupCell11Resistance
					DisplayString,
				batGroupCell11Temp
					DisplayString,
				batGroupCell12Volt
					DisplayString,
				batGroupCell12Resistance
					DisplayString,
				batGroupCell12Temp
					DisplayString,
				batGroupCell13Volt
					DisplayString,
				batGroupCell13Resistance
					DisplayString,
				batGroupCell13Temp
					DisplayString,
				batGroupCell14Volt
					DisplayString,
				batGroupCell14Resistance
					DisplayString,
				batGroupCell14Temp
					DisplayString,
				batGroupCell15Volt
					DisplayString,
				batGroupCell15Resistance
					DisplayString,
				batGroupCell15Temp
					DisplayString,
				batGroupCell16Volt
					DisplayString,
				batGroupCell16Resistance
					DisplayString,
				batGroupCell16Temp
					DisplayString,
				batGroupCell17Volt
					DisplayString,
				batGroupCell17Resistance
					DisplayString,
				batGroupCell17Temp
					DisplayString,
				batGroupCell18Volt
					DisplayString,
				batGroupCell18Resistance
					DisplayString,
				batGroupCell18Temp
					DisplayString,
				batGroupCell19Volt
					DisplayString,
				batGroupCell19Resistance
					DisplayString,
				batGroupCell19Temp
					DisplayString,
				batGroupCell20Volt
					DisplayString,
				batGroupCell20Resistance
					DisplayString,
				batGroupCell20Temp
					DisplayString
			 }

--     1.3.6.1.4.1.41475.3.1.5.4.9.1.1
-- 1.3.6.1.4.1.41475.3.1.5.4.9.1.1
-- 1.3.6.1.4.1.41475.3.1.4.3.18.1.1
-- 1.3.6.1.4.1.41475.3.1.4.3.18.1.1
		-- 1.3.6.1.4.1.41475.3.1.4.3.4.1.1
		batGroupIndex OBJECT-TYPE
			SYNTAX Integer32 (1..9999)
			MAX-ACCESS read-only
			STATUS current
			DESCRIPTION
				"Description: The serial number, starting from 1"
			::= { batGroupEntry 1 }

		
		-- 1.3.6.1.4.1.41475.3.1.4.3.4.1.2
		batGroupVolt OBJECT-TYPE
			SYNTAX DisplayString
			UNITS "V"
			MAX-ACCESS read-only
			STATUS current
			DESCRIPTION
				"Description: battery group voltage."
			::= { batGroupEntry 2 }

		
		-- 1.3.6.1.4.1.41475.3.1.4.3.4.1.3
		batGroupCurrent OBJECT-TYPE
			SYNTAX DisplayString
			UNITS "A"
			MAX-ACCESS read-only
			STATUS current
			DESCRIPTION
				"Description: battery group current."
			::= { batGroupEntry 3 }

		
		-- 1.3.6.1.4.1.41475.3.1.4.3.4.1.4
		batGroupChargeCurrentH OBJECT-TYPE
			SYNTAX DisplayString
			MAX-ACCESS read-only
			STATUS current
			DESCRIPTION
				"Description: The battery group charging current is too high.
				Resones: Battery charging current exceeds the alarm limit.
				Values: 0-ok, 1-alarm."
			::= { batGroupEntry 4 }

		
		-- 1.3.6.1.4.1.41475.3.1.4.3.4.1.5
		batGroupDischargeCurrentH OBJECT-TYPE
			SYNTAX DisplayString
			MAX-ACCESS read-only
			STATUS current
			DESCRIPTION
				"Description: The battery group discharging current is too high.
				Resones: Battery charging current exceeds the alarm limit.
				Values: 0-ok, 1-alarm."
			::= { batGroupEntry 5 }

		
		-- 1.3.6.1.4.1.41475.3.1.4.3.4.1.6
		batGroupBreakerStatus OBJECT-TYPE
			SYNTAX DisplayString
			MAX-ACCESS read-only
			STATUS current
			DESCRIPTION
				"Description: The battery group breaker is broken
				Resones: Circuit breaker is disconnected, the battery was cut off, there is the risk of power outages
				Values: 0-ok, 1-broken(alarm)"
			::= { batGroupEntry 6 }

		
		-- 1.3.6.1.4.1.41475.3.1.4.3.4.1.7
		batGroupPositiveFuseStatus OBJECT-TYPE
			SYNTAX DisplayString
			MAX-ACCESS read-only
			STATUS current
			DESCRIPTION
				"Description: The battery group positive fuse has been broken
				Values: 0-ok, 1-broken(alarm)"
			::= { batGroupEntry 7 }

		
		-- 1.3.6.1.4.1.41475.3.1.4.3.4.1.8
		batGroupNegativeFuseStatus OBJECT-TYPE
			SYNTAX DisplayString
			MAX-ACCESS read-only
			STATUS current
			DESCRIPTION
				"Description: The battery group negative positive fuse has been broken
				Values: 0-ok, 1-broken(alarm)"
			::= { batGroupEntry 8 }

		
--     1.3.6.1.4.1.41475.3.1.5.4.9.1.2
-- 1.3.6.1.4.1.41475.3.1.5.4.9.1.2
-- 1.3.6.1.4.1.41475.3.1.4.3.18.1.5
-- 1.3.6.1.4.1.41475.3.1.4.3.18.1.5
		-- 1.3.6.1.4.1.41475.3.1.4.3.4.1.9
		batGroupVoltUneven OBJECT-TYPE
			SYNTAX DisplayString
			MAX-ACCESS read-only
			STATUS current
			DESCRIPTION
				"Description: The battery voltage is Uneven
				Reasons: The difference between the battery voltage and battery in a single voltage exceeds the alarm limit.
				Values: 0-ok, 1-alarm"
			::= { batGroupEntry 9 }

		
--     1.3.6.1.4.1.41475.3.1.5.4.9.1.2
-- 1.3.6.1.4.1.41475.3.1.5.4.9.1.2
-- 1.3.6.1.4.1.41475.3.1.4.3.18.1.6
-- 1.3.6.1.4.1.41475.3.1.4.3.18.1.6
		-- 1.3.6.1.4.1.41475.3.1.4.3.4.1.10
		batGroupResistanceUneven OBJECT-TYPE
			SYNTAX DisplayString
			MAX-ACCESS read-only
			STATUS current
			DESCRIPTION
				"Description: The battery Resistance is Uneven
				Reasons: The difference between the battery Resistance and battery in a single Resistance exceeds the alarm limit.
				Values: 0-ok, 1-alarm"
			::= { batGroupEntry 10 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.11
		batGroupCell1Volt OBJECT-TYPE
			SYNTAX DisplayString
			UNITS "V"
			MAX-ACCESS read-only
			STATUS current
			DESCRIPTION
				"Description: The battery cell 1 voltage"
			::= { batGroupEntry 11 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.12
		batGroupCell1Resistance OBJECT-TYPE
			SYNTAX DisplayString
			UNITS "m¦¸"
			MAX-ACCESS read-only
			STATUS current
			DESCRIPTION
				"Description. The battery cell 1 Resistance"
			::= { batGroupEntry 12 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.13
		batGroupCell1Temp OBJECT-TYPE
			SYNTAX DisplayString
			UNITS "¡æ"
			MAX-ACCESS read-only
			STATUS current
			DESCRIPTION
				"Description. The battery cell 1 temperature."
			::= { batGroupEntry 13 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.14
		batGroupCell2Volt OBJECT-TYPE
			SYNTAX DisplayString
			UNITS "V"
			MAX-ACCESS read-only
			STATUS current
			DESCRIPTION
				"Description: The battery cell 2 voltage"
			::= { batGroupEntry 14 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.15
		batGroupCell2Resistance OBJECT-TYPE
			SYNTAX DisplayString
			UNITS "m¦¸"
			MAX-ACCESS read-only
			STATUS current
			DESCRIPTION
				"Description. The battery cell 2 Resistance"
			::= { batGroupEntry 15 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.16
		batGroupCell2Temp OBJECT-TYPE
			SYNTAX DisplayString
			UNITS "¡æ"
			MAX-ACCESS read-only
			STATUS current
			DESCRIPTION
				"Description. The battery cell 2 temperature."
			::= { batGroupEntry 16 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.17
		batGroupCell3Volt OBJECT-TYPE
			SYNTAX DisplayString
			UNITS "V"
			MAX-ACCESS read-only
			STATUS current
			DESCRIPTION
				"Description: The battery cell 3 voltage"
			::= { batGroupEntry 17 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.18
		batGroupCell3Resistance OBJECT-TYPE
			SYNTAX DisplayString
			UNITS "m¦¸"
			MAX-ACCESS read-only
			STATUS current
			DESCRIPTION
				"Description. The battery cell 3 Resistance"
			::= { batGroupEntry 18 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.19
		batGroupCell3Temp OBJECT-TYPE
			SYNTAX DisplayString
			UNITS "¡æ"
			MAX-ACCESS read-only
			STATUS current
			DESCRIPTION
				"Description. The battery cell 3 temperature."
			::= { batGroupEntry 19 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.20
		batGroupCell4Volt OBJECT-TYPE
			SYNTAX DisplayString
			UNITS "V"
			MAX-ACCESS read-only
			STATUS current
			DESCRIPTION
				"Description: The battery cell 4 voltage"
			::= { batGroupEntry 20 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.21
		batGroupCell4Resistance OBJECT-TYPE
			SYNTAX DisplayString
			UNITS "m¦¸"
			MAX-ACCESS read-only
			STATUS current
			DESCRIPTION
				"Description. The battery cell 4 Resistance"
			::= { batGroupEntry 21 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.22
		batGroupCell4Temp OBJECT-TYPE
			SYNTAX DisplayString
			UNITS "¡æ"
			MAX-ACCESS read-only
			STATUS current
			DESCRIPTION
				"Description. The battery cell 4 temperature."
			::= { batGroupEntry 22 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.23
		batGroupCell5Volt OBJECT-TYPE
			SYNTAX DisplayString
			UNITS "V"
			MAX-ACCESS read-only
			STATUS current
			DESCRIPTION
				"Description: The battery cell 5 voltage"
			::= { batGroupEntry 23 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.24
		batGroupCell5Resistance OBJECT-TYPE
			SYNTAX DisplayString
			UNITS "m¦¸"
			MAX-ACCESS read-only
			STATUS current
			DESCRIPTION
				"Description. The battery cell 5 Resistance"
			::= { batGroupEntry 24 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.25
		batGroupCell5Temp OBJECT-TYPE
			SYNTAX DisplayString
			UNITS "¡æ"
			MAX-ACCESS read-only
			STATUS current
			DESCRIPTION
				"Description. The battery cell 5 temperature."
			::= { batGroupEntry 25 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.26
		batGroupCell6Volt OBJECT-TYPE
			SYNTAX DisplayString
			UNITS "V"
			MAX-ACCESS read-only
			STATUS current
			DESCRIPTION
				"Description: The battery cell 6 voltage"
			::= { batGroupEntry 26 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.27
		batGroupCell6Resistance OBJECT-TYPE
			SYNTAX DisplayString
			UNITS "m¦¸"
			MAX-ACCESS read-only
			STATUS current
			DESCRIPTION
				"Description. The battery cell 6 Resistance"
			::= { batGroupEntry 27 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.28
		batGroupCell6Temp OBJECT-TYPE
			SYNTAX DisplayString
			UNITS "¡æ"
			MAX-ACCESS read-only
			STATUS current
			DESCRIPTION
				"Description. The battery cell 6 temperature."
			::= { batGroupEntry 28 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.29
		batGroupCell7Volt OBJECT-TYPE
			SYNTAX DisplayString
			UNITS "V"
			MAX-ACCESS read-only
			STATUS current
			DESCRIPTION
				"Description: The battery cell 7 voltage"
			::= { batGroupEntry 29 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.30
		batGroupCell7Resistance OBJECT-TYPE
			SYNTAX DisplayString
			UNITS "m¦¸"
			MAX-ACCESS read-only
			STATUS current
			DESCRIPTION
				"Description. The battery cell 7 Resistance"
			::= { batGroupEntry 30 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.31
		batGroupCell7Temp OBJECT-TYPE
			SYNTAX DisplayString
			UNITS "¡æ"
			MAX-ACCESS read-only
			STATUS current
			DESCRIPTION
				"Description. The battery cell 7 temperature."
			::= { batGroupEntry 31 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.32
		batGroupCell8Volt OBJECT-TYPE
			SYNTAX DisplayString
			UNITS "V"
			MAX-ACCESS read-only
			STATUS current
			DESCRIPTION
				"Description: The battery cell 8 voltage"
			::= { batGroupEntry 32 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.33
		batGroupCell8Resistance OBJECT-TYPE
			SYNTAX DisplayString
			UNITS "m¦¸"
			MAX-ACCESS read-only
			STATUS current
			DESCRIPTION
				"Description. The battery cell 8 Resistance"
			::= { batGroupEntry 33 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.34
		batGroupCell8Temp OBJECT-TYPE
			SYNTAX DisplayString
			UNITS "¡æ"
			MAX-ACCESS read-only
			STATUS current
			DESCRIPTION
				"Description. The battery cell 8 temperature."
			::= { batGroupEntry 34 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.35
		batGroupCell9Volt OBJECT-TYPE
			SYNTAX DisplayString
			UNITS "V"
			MAX-ACCESS read-only
			STATUS current
			DESCRIPTION
				"Description: The battery cell 9 voltage"
			::= { batGroupEntry 35 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.36
		batGroupCell9Resistance OBJECT-TYPE
			SYNTAX DisplayString
			UNITS "m¦¸"
			MAX-ACCESS read-only
			STATUS current
			DESCRIPTION
				"Description. The battery cell 9 Resistance"
			::= { batGroupEntry 36 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.37
		batGroupCell9Temp OBJECT-TYPE
			SYNTAX DisplayString
			UNITS "¡æ"
			MAX-ACCESS read-only
			STATUS current
			DESCRIPTION
				"Description. The battery cell 9 temperature."
			::= { batGroupEntry 37 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.38
		batGroupCell10Volt OBJECT-TYPE
			SYNTAX DisplayString
			UNITS "V"
			MAX-ACCESS read-only
			STATUS current
			DESCRIPTION
				"Description: The battery cell 10 voltage"
			::= { batGroupEntry 38 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.39
		batGroupCell10Resistance OBJECT-TYPE
			SYNTAX DisplayString
			UNITS "m¦¸"
			MAX-ACCESS read-only
			STATUS current
			DESCRIPTION
				"Description. The battery cell 10 Resistance"
			::= { batGroupEntry 39 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.40
		batGroupCell10Temp OBJECT-TYPE
			SYNTAX DisplayString
			UNITS "¡æ"
			MAX-ACCESS read-only
			STATUS current
			DESCRIPTION
				"Description. The battery cell 10 temperature."
			::= { batGroupEntry 40 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.41
		batGroupCell11Volt OBJECT-TYPE
			SYNTAX DisplayString
			UNITS "V"
			MAX-ACCESS read-only
			STATUS current
			DESCRIPTION
				"Description: The battery cell 11 voltage"
			::= { batGroupEntry 41 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.42
		batGroupCell11Resistance OBJECT-TYPE
			SYNTAX DisplayString
			UNITS "m¦¸"
			MAX-ACCESS read-only
			STATUS current
			DESCRIPTION
				"Description. The battery cell 11 Resistance"
			::= { batGroupEntry 42 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.43
		batGroupCell11Temp OBJECT-TYPE
			SYNTAX DisplayString
			UNITS "¡æ"
			MAX-ACCESS read-only
			STATUS current
			DESCRIPTION
				"Description. The battery cell 11 temperature."
			::= { batGroupEntry 43 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.44
		batGroupCell12Volt OBJECT-TYPE
			SYNTAX DisplayString
			UNITS "V"
			MAX-ACCESS read-only
			STATUS current
			DESCRIPTION
				"Description: The battery cell 12 voltage"
			::= { batGroupEntry 44 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.45
		batGroupCell12Resistance OBJECT-TYPE
			SYNTAX DisplayString
			UNITS "m¦¸"
			MAX-ACCESS read-only
			STATUS current
			DESCRIPTION
				"Description. The battery cell 12 Resistance"
			::= { batGroupEntry 45 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.46
		batGroupCell12Temp OBJECT-TYPE
			SYNTAX DisplayString
			UNITS "¡æ"
			MAX-ACCESS read-only
			STATUS current
			DESCRIPTION
				"Description. The battery cell 12 temperature."
			::= { batGroupEntry 46 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.47
		batGroupCell13Volt OBJECT-TYPE
			SYNTAX DisplayString
			UNITS "V"
			MAX-ACCESS read-only
			STATUS current
			DESCRIPTION
				"Description: The battery cell 13 voltage"
			::= { batGroupEntry 47 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.48
		batGroupCell13Resistance OBJECT-TYPE
			SYNTAX DisplayString
			UNITS "m¦¸"
			MAX-ACCESS read-only
			STATUS current
			DESCRIPTION
				"Description. The battery cell 13 Resistance"
			::= { batGroupEntry 48 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.49
		batGroupCell13Temp OBJECT-TYPE
			SYNTAX DisplayString
			UNITS "¡æ"
			MAX-ACCESS read-only
			STATUS current
			DESCRIPTION
				"Description. The battery cell 13 temperature."
			::= { batGroupEntry 49 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.50
		batGroupCell14Volt OBJECT-TYPE
			SYNTAX DisplayString
			UNITS "V"
			MAX-ACCESS read-only
			STATUS current
			DESCRIPTION
				"Description: The battery cell 14 voltage"
			::= { batGroupEntry 50 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.51
		batGroupCell14Resistance OBJECT-TYPE
			SYNTAX DisplayString
			UNITS "m¦¸"
			MAX-ACCESS read-only
			STATUS current
			DESCRIPTION
				"Description. The battery cell 14 Resistance"
			::= { batGroupEntry 51 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.52
		batGroupCell14Temp OBJECT-TYPE
			SYNTAX DisplayString
			UNITS "¡æ"
			MAX-ACCESS read-only
			STATUS current
			DESCRIPTION
				"Description. The battery cell 14 temperature."
			::= { batGroupEntry 52 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.53
		batGroupCell15Volt OBJECT-TYPE
			SYNTAX DisplayString
			UNITS "V"
			MAX-ACCESS read-only
			STATUS current
			DESCRIPTION
				"Description: The battery cell 15 voltage"
			::= { batGroupEntry 53 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.54
		batGroupCell15Resistance OBJECT-TYPE
			SYNTAX DisplayString
			UNITS "m¦¸"
			MAX-ACCESS read-only
			STATUS current
			DESCRIPTION
				"Description. The battery cell 15 Resistance"
			::= { batGroupEntry 54 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.55
		batGroupCell15Temp OBJECT-TYPE
			SYNTAX DisplayString
			UNITS "¡æ"
			MAX-ACCESS read-only
			STATUS current
			DESCRIPTION
				"Description. The battery cell 15 temperature."
			::= { batGroupEntry 55 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.56
		batGroupCell16Volt OBJECT-TYPE
			SYNTAX DisplayString
			UNITS "V"
			MAX-ACCESS read-only
			STATUS current
			DESCRIPTION
				"Description: The battery cell 16 voltage"
			::= { batGroupEntry 56 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.57
		batGroupCell16Resistance OBJECT-TYPE
			SYNTAX DisplayString
			UNITS "m¦¸"
			MAX-ACCESS read-only
			STATUS current
			DESCRIPTION
				"Description. The battery cell 16 Resistance"
			::= { batGroupEntry 57 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.58
		batGroupCell16Temp OBJECT-TYPE
			SYNTAX DisplayString
			UNITS "¡æ"
			MAX-ACCESS read-only
			STATUS current
			DESCRIPTION
				"Description. The battery cell 16 temperature."
			::= { batGroupEntry 58 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.59
		batGroupCell17Volt OBJECT-TYPE
			SYNTAX DisplayString
			UNITS "V"
			MAX-ACCESS read-only
			STATUS current
			DESCRIPTION
				"Description: The battery cell 17 voltage"
			::= { batGroupEntry 59 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.60
		batGroupCell17Resistance OBJECT-TYPE
			SYNTAX DisplayString
			UNITS "m¦¸"
			MAX-ACCESS read-only
			STATUS current
			DESCRIPTION
				"Description. The battery cell 17 Resistance"
			::= { batGroupEntry 60 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.61
		batGroupCell17Temp OBJECT-TYPE
			SYNTAX DisplayString
			UNITS "¡æ"
			MAX-ACCESS read-only
			STATUS current
			DESCRIPTION
				"Description. The battery cell 17 temperature."
			::= { batGroupEntry 61 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.62
		batGroupCell18Volt OBJECT-TYPE
			SYNTAX DisplayString
			UNITS "V"
			MAX-ACCESS read-only
			STATUS current
			DESCRIPTION
				"Description: The battery cell 18 voltage"
			::= { batGroupEntry 62 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.63
		batGroupCell18Resistance OBJECT-TYPE
			SYNTAX DisplayString
			UNITS "m¦¸"
			MAX-ACCESS read-only
			STATUS current
			DESCRIPTION
				"Description. The battery cell 18 Resistance"
			::= { batGroupEntry 63 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.64
		batGroupCell18Temp OBJECT-TYPE
			SYNTAX DisplayString
			UNITS "¡æ"
			MAX-ACCESS read-only
			STATUS current
			DESCRIPTION
				"Description. The battery cell 18 temperature."
			::= { batGroupEntry 64 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.65
		batGroupCell19Volt OBJECT-TYPE
			SYNTAX DisplayString
			UNITS "V"
			MAX-ACCESS read-only
			STATUS current
			DESCRIPTION
				"Description: The battery cell 19 voltage"
			::= { batGroupEntry 65 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.66
		batGroupCell19Resistance OBJECT-TYPE
			SYNTAX DisplayString
			UNITS "m¦¸"
			MAX-ACCESS read-only
			STATUS current
			DESCRIPTION
				"Description. The battery cell 19 Resistance"
			::= { batGroupEntry 66 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.67
		batGroupCell19Temp OBJECT-TYPE
			SYNTAX DisplayString
			UNITS "¡æ"
			MAX-ACCESS read-only
			STATUS current
			DESCRIPTION
				"Description. The battery cell 19 temperature."
			::= { batGroupEntry 67 }

		
--     1.3.6.1.4.1.41475.3.1.5.4.9.1.2
-- 1.3.6.1.4.1.41475.3.1.5.4.9.1.2
-- 1.3.6.1.4.1.41475.3.1.4.3.18.1.2
-- 1.3.6.1.4.1.41475.3.1.4.3.18.1.2
		-- 1.3.6.1.4.1.41475.3.1.4.3.4.1.68
		batGroupCell20Volt OBJECT-TYPE
			SYNTAX DisplayString
			UNITS "V"
			MAX-ACCESS read-only
			STATUS current
			DESCRIPTION
				"Description: The battery cell 20 voltage"
			::= { batGroupEntry 68 }

		
--     1.3.6.1.4.1.41475.3.1.5.4.9.1.3
-- 1.3.6.1.4.1.41475.3.1.5.4.9.1.3
-- 1.3.6.1.4.1.41475.3.1.4.3.18.1.3
-- 1.3.6.1.4.1.41475.3.1.4.3.18.1.3
		-- 1.3.6.1.4.1.41475.3.1.4.3.4.1.69
		batGroupCell20Resistance OBJECT-TYPE
			SYNTAX DisplayString
			UNITS "m¦¸"
			MAX-ACCESS read-only
			STATUS current
			DESCRIPTION
				"Description. The battery cell 20 Resistance"
			::= { batGroupEntry 69 }

		
--     1.3.6.1.4.1.41475.3.1.5.4.9.1.4
-- 1.3.6.1.4.1.41475.3.1.5.4.9.1.4
-- 1.3.6.1.4.1.41475.3.1.4.3.18.1.4
-- 1.3.6.1.4.1.41475.3.1.4.3.18.1.4
		-- 1.3.6.1.4.1.41475.3.1.4.3.4.1.70
		batGroupCell20Temp OBJECT-TYPE
			SYNTAX DisplayString
			UNITS "¡æ"
			MAX-ACCESS read-only
			STATUS current
			DESCRIPTION
				"Description. The battery cell 20 temperature."
			::= { batGroupEntry 70 }

		
--     1.3.6.1.4.1.41475.3.1.5.6
-- 1.3.6.1.4.1.41475.3.1.5.6
-- 1.3.6.1.4.1.41475.3.1.4.5
-- 1.3.6.1.4.1.41475.3.1.4.5
		-- 1.3.6.1.4.1.41475.3.1.4.4
		acPdu OBJECT IDENTIFIER ::= { tmdcMonObjects 4 }

		
--     1.3.6.1.4.1.41475.3.1.5.6.1
-- 1.3.6.1.4.1.41475.3.1.5.6.1
-- 1.3.6.1.4.1.41475.3.1.4.5.1
-- 1.3.6.1.4.1.41475.3.1.4.5.1
		-- 1.3.6.1.4.1.41475.3.1.4.4.1
		acPduTable OBJECT-TYPE
			SYNTAX SEQUENCE OF AcPduEntry
			MAX-ACCESS not-accessible
			STATUS current
			DESCRIPTION
				"Description."
			::= { acPdu 1 }

		
--     1.3.6.1.4.1.41475.3.1.5.6.1.1
-- 1.3.6.1.4.1.41475.3.1.5.6.1.1
-- 1.3.6.1.4.1.41475.3.1.4.5.1.1
-- 1.3.6.1.4.1.41475.3.1.4.5.1.1
		-- 1.3.6.1.4.1.41475.3.1.4.4.1.1
		acPduEntry OBJECT-TYPE
			SYNTAX AcPduEntry
			MAX-ACCESS not-accessible
			STATUS current
			DESCRIPTION
				"Description."
			INDEX { acPduIndex }
			::= { acPduTable 1 }

		
		AcPduEntry ::=
			SEQUENCE { 
				acPduIndex
					Integer32,
				acRackLabel
					DisplayString,
				acPduVoltageA
					DisplayString,
				acPduVoltageB
					DisplayString,
				acPduVoltageC
					DisplayString,
				acPduCurrentA
					DisplayString,
				acPduCurrentB
					DisplayString,
				acPduCurrentC
					DisplayString,
				acPduCircuitBreakerA
					DisplayString,
				acPduCircuitBreakerB
					DisplayString,
				acPduCircuitBreakerC
					DisplayString,
				acPduPowerA
					DisplayString,
				acPduPowerB
					DisplayString,
				acPduPowerC
					DisplayString
			 }

--     1.3.6.1.4.1.41475.3.1.5.6.1.1.1
-- 1.3.6.1.4.1.41475.3.1.5.6.1.1.1
-- 1.3.6.1.4.1.41475.3.1.4.5.1.1.1
-- 1.3.6.1.4.1.41475.3.1.4.5.1.1.1
		-- 1.3.6.1.4.1.41475.3.1.4.4.1.1.1
		acPduIndex OBJECT-TYPE
			SYNTAX Integer32 (1..9999)
			MAX-ACCESS read-only
			STATUS current
			DESCRIPTION
				"Description: The serial number, starting from 1"
			::= { acPduEntry 1 }

		
--   1.3.6.1.4.1.41475.3.1.4.5.1.1.2
-- 1.3.6.1.4.1.41475.3.1.4.5.1.1.2
		-- 1.3.6.1.4.1.41475.3.1.4.4.1.1.2
		acRackLabel OBJECT-TYPE
			SYNTAX DisplayString
			MAX-ACCESS read-only
			STATUS current
			DESCRIPTION
				"Description."
			::= { acPduEntry 2 }

		
--     1.3.6.1.4.1.41475.3.1.5.6.1.1.4
-- 1.3.6.1.4.1.41475.3.1.5.6.1.1.4
-- 1.3.6.1.4.1.41475.3.1.4.5.1.1.3
-- 1.3.6.1.4.1.41475.3.1.4.5.1.1.3
		-- 1.3.6.1.4.1.41475.3.1.4.4.1.1.3
		acPduVoltageA OBJECT-TYPE
			SYNTAX DisplayString
			UNITS "V"
			MAX-ACCESS read-only
			STATUS current
			DESCRIPTION
				"Description: pdu-A voltage"
			::= { acPduEntry 3 }

		
--     1.3.6.1.4.1.41475.3.1.5.6.1.1.4
-- 1.3.6.1.4.1.41475.3.1.5.6.1.1.4
-- 1.3.6.1.4.1.41475.3.1.4.5.1.1.3
-- 1.3.6.1.4.1.41475.3.1.4.5.1.1.3
		-- 1.3.6.1.4.1.41475.3.1.4.4.1.1.4
		acPduVoltageB OBJECT-TYPE
			SYNTAX DisplayString
			UNITS "V"
			MAX-ACCESS read-only
			STATUS current
			DESCRIPTION
				"Description: pdu-B voltage"
			::= { acPduEntry 4 }

		
--     1.3.6.1.4.1.41475.3.1.5.6.1.1.4
-- 1.3.6.1.4.1.41475.3.1.5.6.1.1.4
-- 1.3.6.1.4.1.41475.3.1.4.5.1.1.3
-- 1.3.6.1.4.1.41475.3.1.4.5.1.1.3
		-- 1.3.6.1.4.1.41475.3.1.4.4.1.1.5
		acPduVoltageC OBJECT-TYPE
			SYNTAX DisplayString
			UNITS "V"
			MAX-ACCESS read-only
			STATUS current
			DESCRIPTION
				"Description: pdu-C voltage"
			::= { acPduEntry 5 }

		
--     1.3.6.1.4.1.41475.3.1.5.6.1.1.4
-- 1.3.6.1.4.1.41475.3.1.5.6.1.1.4
-- 1.3.6.1.4.1.41475.3.1.4.5.1.1.3
-- 1.3.6.1.4.1.41475.3.1.4.5.1.1.3
		-- 1.3.6.1.4.1.41475.3.1.4.4.1.1.6
		acPduCurrentA OBJECT-TYPE
			SYNTAX DisplayString
			UNITS "A"
			MAX-ACCESS read-only
			STATUS current
			DESCRIPTION
				"Description: pdu-A current"
			::= { acPduEntry 6 }

		
--     1.3.6.1.4.1.41475.3.1.5.6.1.1.4
-- 1.3.6.1.4.1.41475.3.1.5.6.1.1.4
-- 1.3.6.1.4.1.41475.3.1.4.5.1.1.4
-- 1.3.6.1.4.1.41475.3.1.4.5.1.1.4
		-- 1.3.6.1.4.1.41475.3.1.4.4.1.1.7
		acPduCurrentB OBJECT-TYPE
			SYNTAX DisplayString
			UNITS "A"
			MAX-ACCESS read-only
			STATUS current
			DESCRIPTION
				"Description: pdu-B current"
			::= { acPduEntry 7 }

		
--     1.3.6.1.4.1.41475.3.1.5.6.1.1.4
-- 1.3.6.1.4.1.41475.3.1.5.6.1.1.4
-- 1.3.6.1.4.1.41475.3.1.4.5.1.1.5
-- 1.3.6.1.4.1.41475.3.1.4.5.1.1.5
		-- 1.3.6.1.4.1.41475.3.1.4.4.1.1.8
		acPduCurrentC OBJECT-TYPE
			SYNTAX DisplayString
			UNITS "A"
			MAX-ACCESS read-only
			STATUS current
			DESCRIPTION
				"Description: pdu-C current"
			::= { acPduEntry 8 }

		
--     1.3.6.1.4.1.41475.3.1.5.6.1.1.4
-- 1.3.6.1.4.1.41475.3.1.5.6.1.1.4
-- 1.3.6.1.4.1.41475.3.1.4.5.1.1.6
-- 1.3.6.1.4.1.41475.3.1.4.5.1.1.6
		-- 1.3.6.1.4.1.41475.3.1.4.4.1.1.9
		acPduCircuitBreakerA OBJECT-TYPE
			SYNTAX DisplayString
			MAX-ACCESS read-only
			STATUS current
			DESCRIPTION
				"Description: AC pdu-A circuit breaker.
				Reasons: The circuit breaker is in the off state
				Values: 0-close, 1-open"
			::= { acPduEntry 9 }

		
--     1.3.6.1.4.1.41475.3.1.5.6.1.1.4
-- 1.3.6.1.4.1.41475.3.1.5.6.1.1.4
-- 1.3.6.1.4.1.41475.3.1.4.5.1.1.7
-- 1.3.6.1.4.1.41475.3.1.4.5.1.1.7
		-- 1.3.6.1.4.1.41475.3.1.4.4.1.1.10
		acPduCircuitBreakerB OBJECT-TYPE
			SYNTAX DisplayString
			MAX-ACCESS read-only
			STATUS current
			DESCRIPTION
				"Description: AC pdu-B circuit breaker.
				Reasons: The circuit breaker is in the off state
				Values: 0-close, 1-open"
			::= { acPduEntry 10 }

		
--     1.3.6.1.4.1.41475.3.1.5.6.1.1.4
-- 1.3.6.1.4.1.41475.3.1.5.6.1.1.4
-- 1.3.6.1.4.1.41475.3.1.4.5.1.1.8
-- 1.3.6.1.4.1.41475.3.1.4.5.1.1.8
		-- 1.3.6.1.4.1.41475.3.1.4.4.1.1.11
		acPduCircuitBreakerC OBJECT-TYPE
			SYNTAX DisplayString
			MAX-ACCESS read-only
			STATUS current
			DESCRIPTION
				"Description: AC pdu-C circuit breaker.
				Reasons: The circuit breaker is in the off state
				Values: 0-close, 1-open"
			::= { acPduEntry 11 }

		
--     1.3.6.1.4.1.41475.3.1.5.6.1.1.4
-- 1.3.6.1.4.1.41475.3.1.5.6.1.1.4
-- 1.3.6.1.4.1.41475.3.1.4.5.1.1.9
-- 1.3.6.1.4.1.41475.3.1.4.5.1.1.9
		-- 1.3.6.1.4.1.41475.3.1.4.4.1.1.12
		acPduPowerA OBJECT-TYPE
			SYNTAX DisplayString
			UNITS "kW"
			MAX-ACCESS read-only
			STATUS current
			DESCRIPTION
				"Description: pdu-A power"
			::= { acPduEntry 12 }

		
--     1.3.6.1.4.1.41475.3.1.5.6.1.1.4
-- 1.3.6.1.4.1.41475.3.1.5.6.1.1.4
-- 1.3.6.1.4.1.41475.3.1.4.5.1.1.10
-- 1.3.6.1.4.1.41475.3.1.4.5.1.1.10
		-- 1.3.6.1.4.1.41475.3.1.4.4.1.1.13
		acPduPowerB OBJECT-TYPE
			SYNTAX DisplayString
			UNITS "kW"
			MAX-ACCESS read-only
			STATUS current
			DESCRIPTION
				"Description: pdu-B power"
			::= { acPduEntry 13 }

		
--     1.3.6.1.4.1.41475.3.1.5.6.1.1.4
-- 1.3.6.1.4.1.41475.3.1.5.6.1.1.4
-- 1.3.6.1.4.1.41475.3.1.4.5.1.1.11
-- 1.3.6.1.4.1.41475.3.1.4.5.1.1.11
		-- 1.3.6.1.4.1.41475.3.1.4.4.1.1.14
		acPduPowerC OBJECT-TYPE
			SYNTAX DisplayString
			UNITS "kW"
			MAX-ACCESS read-only
			STATUS current
			DESCRIPTION
				"Description: pdu-C power"
			::= { acPduEntry 14 }

		
--     1.3.6.1.4.1.41475.3.1.5.7
-- 1.3.6.1.4.1.41475.3.1.5.7
-- 1.3.6.1.4.1.41475.3.1.4.6
-- 1.3.6.1.4.1.41475.3.1.4.6
		-- 1.3.6.1.4.1.41475.3.1.4.5
		dcPdu OBJECT IDENTIFIER ::= { tmdcMonObjects 5 }

		
--     1.3.6.1.4.1.41475.3.1.5.7.1
-- 1.3.6.1.4.1.41475.3.1.5.7.1
-- 1.3.6.1.4.1.41475.3.1.4.6.1
-- 1.3.6.1.4.1.41475.3.1.4.6.1
		-- 1.3.6.1.4.1.41475.3.1.4.5.1
		dcPduTable OBJECT-TYPE
			SYNTAX SEQUENCE OF DcPduEntry
			MAX-ACCESS not-accessible
			STATUS current
			DESCRIPTION
				"Description."
			::= { dcPdu 1 }

		
--     1.3.6.1.4.1.41475.3.1.5.7.1.1
-- 1.3.6.1.4.1.41475.3.1.5.7.1.1
-- 1.3.6.1.4.1.41475.3.1.4.6.1.1
-- 1.3.6.1.4.1.41475.3.1.4.6.1.1
		-- 1.3.6.1.4.1.41475.3.1.4.5.1.1
		dcPduEntry OBJECT-TYPE
			SYNTAX DcPduEntry
			MAX-ACCESS not-accessible
			STATUS current
			DESCRIPTION
				"Description."
			INDEX { dcPduIndex }
			::= { dcPduTable 1 }

		
		DcPduEntry ::=
			SEQUENCE { 
				dcPduIndex
					Integer32,
				dcRackLabel
					DisplayString,
				dcPduAVoltage
					DisplayString,
				dcPduBVoltage
					DisplayString,
				dcPduCVoltage
					DisplayString,
				dcPduDVoltage
					DisplayString,
				dcPduACurrent
					DisplayString,
				dcPduBCurrent
					DisplayString,
				dcPduCCurrent
					DisplayString,
				dcPduDCurrent
					DisplayString,
				dcPduACircuitBreaker
					DisplayString,
				dcPduAOvercurrent
					DisplayString,
				dcPduBCircuitBreaker
					DisplayString,
				dcPduBOvercurrent
					DisplayString,
				dcPduCCircuitBreaker
					DisplayString,
				dcPduCOvercurrent
					DisplayString,
				dcPduDCircuitBreaker
					DisplayString,
				dcPduDOvercurrent
					DisplayString,
				dcPduAPower
					DisplayString,
				dcPduBPower
					DisplayString,
				dcPduCPower
					DisplayString,
				dcPduDPower
					DisplayString
			 }

--     1.3.6.1.4.1.41475.3.1.5.7.1.1.1
-- 1.3.6.1.4.1.41475.3.1.5.7.1.1.1
-- 1.3.6.1.4.1.41475.3.1.4.6.1.1.1
-- 1.3.6.1.4.1.41475.3.1.4.6.1.1.1
		-- 1.3.6.1.4.1.41475.3.1.4.5.1.1.1
		dcPduIndex OBJECT-TYPE
			SYNTAX Integer32 (1..9999)
			MAX-ACCESS read-only
			STATUS current
			DESCRIPTION
				"Description: The serial number, starting from 1"
			::= { dcPduEntry 1 }

		
--   1.3.6.1.4.1.41475.3.1.4.6.1.1.2
-- 1.3.6.1.4.1.41475.3.1.4.6.1.1.2
		-- 1.3.6.1.4.1.41475.3.1.4.5.1.1.2
		dcRackLabel OBJECT-TYPE
			SYNTAX DisplayString
			MAX-ACCESS read-only
			STATUS current
			DESCRIPTION
				"Description."
			::= { dcPduEntry 2 }

		
--     1.3.6.1.4.1.41475.3.1.5.7.1.1.4
-- 1.3.6.1.4.1.41475.3.1.5.7.1.1.4
-- 1.3.6.1.4.1.41475.3.1.4.6.1.1.3
-- 1.3.6.1.4.1.41475.3.1.4.6.1.1.3
		-- 1.3.6.1.4.1.41475.3.1.4.5.1.1.3
		dcPduAVoltage OBJECT-TYPE
			SYNTAX DisplayString
			UNITS "V"
			MAX-ACCESS read-only
			STATUS current
			DESCRIPTION
				"Description: pdu-A voltage"
			::= { dcPduEntry 3 }

		
--     1.3.6.1.4.1.41475.3.1.5.7.1.1.4
-- 1.3.6.1.4.1.41475.3.1.5.7.1.1.4
-- 1.3.6.1.4.1.41475.3.1.4.6.1.1.3
-- 1.3.6.1.4.1.41475.3.1.4.6.1.1.3
		-- 1.3.6.1.4.1.41475.3.1.4.5.1.1.4
		dcPduBVoltage OBJECT-TYPE
			SYNTAX DisplayString
			UNITS "B"
			MAX-ACCESS read-only
			STATUS current
			DESCRIPTION
				"Description: pdu-B voltage"
			::= { dcPduEntry 4 }

		
--     1.3.6.1.4.1.41475.3.1.5.7.1.1.4
-- 1.3.6.1.4.1.41475.3.1.5.7.1.1.4
-- 1.3.6.1.4.1.41475.3.1.4.6.1.1.3
-- 1.3.6.1.4.1.41475.3.1.4.6.1.1.3
		-- 1.3.6.1.4.1.41475.3.1.4.5.1.1.5
		dcPduCVoltage OBJECT-TYPE
			SYNTAX DisplayString
			UNITS "V"
			MAX-ACCESS read-only
			STATUS current
			DESCRIPTION
				"Description: pdu-C voltage"
			::= { dcPduEntry 5 }

		
--     1.3.6.1.4.1.41475.3.1.5.7.1.1.4
-- 1.3.6.1.4.1.41475.3.1.5.7.1.1.4
-- 1.3.6.1.4.1.41475.3.1.4.6.1.1.3
-- 1.3.6.1.4.1.41475.3.1.4.6.1.1.3
		-- 1.3.6.1.4.1.41475.3.1.4.5.1.1.6
		dcPduDVoltage OBJECT-TYPE
			SYNTAX DisplayString
			UNITS "V"
			MAX-ACCESS read-only
			STATUS current
			DESCRIPTION
				"Description: pdu-D voltage"
			::= { dcPduEntry 6 }

		
--     1.3.6.1.4.1.41475.3.1.5.7.1.1.4
-- 1.3.6.1.4.1.41475.3.1.5.7.1.1.4
-- 1.3.6.1.4.1.41475.3.1.4.6.1.1.3
-- 1.3.6.1.4.1.41475.3.1.4.6.1.1.3
		-- 1.3.6.1.4.1.41475.3.1.4.5.1.1.7
		dcPduACurrent OBJECT-TYPE
			SYNTAX DisplayString
			UNITS "A"
			MAX-ACCESS read-only
			STATUS current
			DESCRIPTION
				"Description: pdu-A current"
			::= { dcPduEntry 7 }

		
--     1.3.6.1.4.1.41475.3.1.5.7.1.1.4
-- 1.3.6.1.4.1.41475.3.1.5.7.1.1.4
-- 1.3.6.1.4.1.41475.3.1.4.6.1.1.4
-- 1.3.6.1.4.1.41475.3.1.4.6.1.1.4
		-- 1.3.6.1.4.1.41475.3.1.4.5.1.1.8
		dcPduBCurrent OBJECT-TYPE
			SYNTAX DisplayString
			UNITS "A"
			MAX-ACCESS read-only
			STATUS current
			DESCRIPTION
				"Description: pdu-B current"
			::= { dcPduEntry 8 }

		
--     1.3.6.1.4.1.41475.3.1.5.7.1.1.4
-- 1.3.6.1.4.1.41475.3.1.5.7.1.1.4
-- 1.3.6.1.4.1.41475.3.1.4.6.1.1.5
-- 1.3.6.1.4.1.41475.3.1.4.6.1.1.5
		-- 1.3.6.1.4.1.41475.3.1.4.5.1.1.9
		dcPduCCurrent OBJECT-TYPE
			SYNTAX DisplayString
			UNITS "A"
			MAX-ACCESS read-only
			STATUS current
			DESCRIPTION
				"Description: pdu-C current"
			::= { dcPduEntry 9 }

		
--     1.3.6.1.4.1.41475.3.1.5.7.1.1.4
-- 1.3.6.1.4.1.41475.3.1.5.7.1.1.4
-- 1.3.6.1.4.1.41475.3.1.4.6.1.1.6
-- 1.3.6.1.4.1.41475.3.1.4.6.1.1.6
		-- 1.3.6.1.4.1.41475.3.1.4.5.1.1.10
		dcPduDCurrent OBJECT-TYPE
			SYNTAX DisplayString
			UNITS "A"
			MAX-ACCESS read-only
			STATUS current
			DESCRIPTION
				"Description: pdu-D current"
			::= { dcPduEntry 10 }

		
--     1.3.6.1.4.1.41475.3.1.5.7.1.1.3
-- 1.3.6.1.4.1.41475.3.1.5.7.1.1.3
-- 1.3.6.1.4.1.41475.3.1.4.6.1.1.7
-- 1.3.6.1.4.1.41475.3.1.4.6.1.1.7
		-- 1.3.6.1.4.1.41475.3.1.4.5.1.1.11
		dcPduACircuitBreaker OBJECT-TYPE
			SYNTAX DisplayString
			MAX-ACCESS read-only
			STATUS current
			DESCRIPTION
				"Description: the state of upper circuit breaker.
				Reasons: The circuit breaker is in the off state
				Values: 0-close, 1-open"
			::= { dcPduEntry 11 }

		
--     1.3.6.1.4.1.41475.3.1.5.7.1.1.5
-- 1.3.6.1.4.1.41475.3.1.5.7.1.1.5
-- 1.3.6.1.4.1.41475.3.1.4.6.1.1.8
-- 1.3.6.1.4.1.41475.3.1.4.6.1.1.8
		-- 1.3.6.1.4.1.41475.3.1.4.5.1.1.12
		dcPduAOvercurrent OBJECT-TYPE
			SYNTAX DisplayString
			MAX-ACCESS read-only
			STATUS current
			DESCRIPTION
				"Description: the state of upper pdu overcurrent.
				Reasons: load overcurrent.
				Values: 0-ok, 1-alarm"
			::= { dcPduEntry 12 }

		
--     1.3.6.1.4.1.41475.3.1.5.7.1.1.3
-- 1.3.6.1.4.1.41475.3.1.5.7.1.1.3
-- 1.3.6.1.4.1.41475.3.1.4.6.1.1.9
-- 1.3.6.1.4.1.41475.3.1.4.6.1.1.9
		-- 1.3.6.1.4.1.41475.3.1.4.5.1.1.13
		dcPduBCircuitBreaker OBJECT-TYPE
			SYNTAX DisplayString
			MAX-ACCESS read-only
			STATUS current
			DESCRIPTION
				"Description: the state of down circuit breaker.
				Reasons: The circuit breaker is in the off state
				Values: 0-close, 1-open"
			::= { dcPduEntry 13 }

		
--     1.3.6.1.4.1.41475.3.1.5.7.1.1.5
-- 1.3.6.1.4.1.41475.3.1.5.7.1.1.5
-- 1.3.6.1.4.1.41475.3.1.4.6.1.1.10
-- 1.3.6.1.4.1.41475.3.1.4.6.1.1.10
		-- 1.3.6.1.4.1.41475.3.1.4.5.1.1.14
		dcPduBOvercurrent OBJECT-TYPE
			SYNTAX DisplayString
			MAX-ACCESS read-only
			STATUS current
			DESCRIPTION
				"Description: the state of down pdu overcurrent.
				Reasons: load overcurrent.
				Values: 0-ok, 1-alarm"
			::= { dcPduEntry 14 }

		
--     1.3.6.1.4.1.41475.3.1.5.7.1.1.3
-- 1.3.6.1.4.1.41475.3.1.5.7.1.1.3
-- 1.3.6.1.4.1.41475.3.1.4.6.1.1.11
-- 1.3.6.1.4.1.41475.3.1.4.6.1.1.11
		-- 1.3.6.1.4.1.41475.3.1.4.5.1.1.15
		dcPduCCircuitBreaker OBJECT-TYPE
			SYNTAX DisplayString
			MAX-ACCESS read-only
			STATUS current
			DESCRIPTION
				"Description: the state of down circuit breaker.
				Reasons: The circuit breaker is in the off state
				Values: 0-close, 1-open"
			::= { dcPduEntry 15 }

		
--     1.3.6.1.4.1.41475.3.1.5.7.1.1.5
-- 1.3.6.1.4.1.41475.3.1.5.7.1.1.5
-- 1.3.6.1.4.1.41475.3.1.4.6.1.1.12
-- 1.3.6.1.4.1.41475.3.1.4.6.1.1.12
		-- 1.3.6.1.4.1.41475.3.1.4.5.1.1.16
		dcPduCOvercurrent OBJECT-TYPE
			SYNTAX DisplayString
			MAX-ACCESS read-only
			STATUS current
			DESCRIPTION
				"Description: the state of down pdu overcurrent.
				Reasons: load overcurrent.
				Values: 0-ok, 1-alarm"
			::= { dcPduEntry 16 }

		
--     1.3.6.1.4.1.41475.3.1.5.7.1.1.3
-- 1.3.6.1.4.1.41475.3.1.5.7.1.1.3
-- 1.3.6.1.4.1.41475.3.1.4.6.1.1.13
-- 1.3.6.1.4.1.41475.3.1.4.6.1.1.13
		-- 1.3.6.1.4.1.41475.3.1.4.5.1.1.17
		dcPduDCircuitBreaker OBJECT-TYPE
			SYNTAX DisplayString
			MAX-ACCESS read-only
			STATUS current
			DESCRIPTION
				"Description: the state of down circuit breaker.
				Reasons: The circuit breaker is in the off state
				Values: 0-close, 1-open"
			::= { dcPduEntry 17 }

		
--     1.3.6.1.4.1.41475.3.1.5.7.1.1.5
-- 1.3.6.1.4.1.41475.3.1.5.7.1.1.5
-- 1.3.6.1.4.1.41475.3.1.4.6.1.1.14
-- 1.3.6.1.4.1.41475.3.1.4.6.1.1.14
		-- 1.3.6.1.4.1.41475.3.1.4.5.1.1.18
		dcPduDOvercurrent OBJECT-TYPE
			SYNTAX DisplayString
			MAX-ACCESS read-only
			STATUS current
			DESCRIPTION
				"Description: the state of down pdu overcurrent.
				Reasons: load overcurrent.
				Values: 0-ok, 1-alarm"
			::= { dcPduEntry 18 }

		
--     1.3.6.1.4.1.41475.3.1.5.6.1.1.4
-- 1.3.6.1.4.1.41475.3.1.5.6.1.1.4
-- 1.3.6.1.4.1.41475.3.1.4.6.1.1.15
-- 1.3.6.1.4.1.41475.3.1.4.6.1.1.15
		-- 1.3.6.1.4.1.41475.3.1.4.5.1.1.19
		dcPduAPower OBJECT-TYPE
			SYNTAX DisplayString
			UNITS "kW"
			MAX-ACCESS read-only
			STATUS current
			DESCRIPTION
				"Description: pdu-A power"
			::= { dcPduEntry 19 }

		
--     1.3.6.1.4.1.41475.3.1.5.6.1.1.4
-- 1.3.6.1.4.1.41475.3.1.5.6.1.1.4
-- 1.3.6.1.4.1.41475.3.1.4.6.1.1.16
-- 1.3.6.1.4.1.41475.3.1.4.6.1.1.16
		-- 1.3.6.1.4.1.41475.3.1.4.5.1.1.20
		dcPduBPower OBJECT-TYPE
			SYNTAX DisplayString
			UNITS "kW"
			MAX-ACCESS read-only
			STATUS current
			DESCRIPTION
				"Description: pdu-B power"
			::= { dcPduEntry 20 }

		
--     1.3.6.1.4.1.41475.3.1.5.6.1.1.4
-- 1.3.6.1.4.1.41475.3.1.5.6.1.1.4
-- 1.3.6.1.4.1.41475.3.1.4.6.1.1.17
-- 1.3.6.1.4.1.41475.3.1.4.6.1.1.17
		-- 1.3.6.1.4.1.41475.3.1.4.5.1.1.21
		dcPduCPower OBJECT-TYPE
			SYNTAX DisplayString
			UNITS "kW"
			MAX-ACCESS read-only
			STATUS current
			DESCRIPTION
				"Description: pdu-C power"
			::= { dcPduEntry 21 }

		
--     1.3.6.1.4.1.41475.3.1.5.6.1.1.4
-- 1.3.6.1.4.1.41475.3.1.5.6.1.1.4
-- 1.3.6.1.4.1.41475.3.1.4.6.1.1.18
-- 1.3.6.1.4.1.41475.3.1.4.6.1.1.18
		-- 1.3.6.1.4.1.41475.3.1.4.5.1.1.22
		dcPduDPower OBJECT-TYPE
			SYNTAX DisplayString
			UNITS "kW"
			MAX-ACCESS read-only
			STATUS current
			DESCRIPTION
				"Description: pdu-D power"
			::= { dcPduEntry 22 }

		
--     1.3.6.1.4.1.41475.3.1.5.8
-- 1.3.6.1.4.1.41475.3.1.5.8
-- 1.3.6.1.4.1.41475.3.1.4.7
-- 1.3.6.1.4.1.41475.3.1.4.7
		-- 1.3.6.1.4.1.41475.3.1.4.6
		airConditioner OBJECT IDENTIFIER ::= { tmdcMonObjects 6 }

		
--     1.3.6.1.4.1.41475.3.1.5.8.1
-- 1.3.6.1.4.1.41475.3.1.5.8.1
-- 1.3.6.1.4.1.41475.3.1.4.7.1
-- 1.3.6.1.4.1.41475.3.1.4.7.1
		-- 1.3.6.1.4.1.41475.3.1.4.6.1
		acTable OBJECT-TYPE
			SYNTAX SEQUENCE OF AcEntry
			MAX-ACCESS not-accessible
			STATUS current
			DESCRIPTION
				"Description."
			::= { airConditioner 1 }

		
--     1.3.6.1.4.1.41475.3.1.5.8.1.1
-- 1.3.6.1.4.1.41475.3.1.5.8.1.1
-- 1.3.6.1.4.1.41475.3.1.4.7.1.1
-- 1.3.6.1.4.1.41475.3.1.4.7.1.1
		-- 1.3.6.1.4.1.41475.3.1.4.6.1.1
		acEntry OBJECT-TYPE
			SYNTAX AcEntry
			MAX-ACCESS not-accessible
			STATUS current
			DESCRIPTION
				"Description."
			INDEX { acIndex }
			::= { acTable 1 }

		
		AcEntry ::=
			SEQUENCE { 
				acIndex
					Integer32,
				acFanSpeed
					DisplayString,
				acWaterValveOpening
					DisplayString,
				acReturnTempUpper
					DisplayString,
				acReturnTempCentral
					DisplayString,
				acReturnTempLower
					DisplayString,
				acReturnHum
					DisplayString,
				acSupplyTempUpper
					DisplayString,
				acSupplyTempCentral
					DisplayString,
				acSupplyTempLower
					DisplayString,
				acSupplyHum
					DisplayString,
				acSupplyWaterTemp
					DisplayString,
				acReturnWaterTemp
					DisplayString,
				acSupplyWaterPressure
					DisplayString,
				acReturnWaterPressure
					DisplayString,
				acWindDifferentialPressure
					DisplayString,
				acRTempSensor1Fault
					DisplayString,
				acRTempSensor2Fault
					DisplayString,
				acRTempSensor3Fault
					DisplayString,
				acSTempSensor1Fault
					DisplayString,
				acSTempSensor2Fault
					DisplayString,
				acSTempSensor3Fault
					DisplayString,
				acRHumSensorFault
					DisplayString,
				acSHumSensorFault
					DisplayString,
				acFan1Fault
					DisplayString,
				acFan2Fault
					DisplayString,
				acFan3Fault
					DisplayString,
				acFan4Fault
					DisplayString,
				acFan5Fault
					DisplayString,
				acFan6Fault
					DisplayString,
				acFan7Fault
					DisplayString,
				acFan8Fault
					DisplayString,
				acFan9Fault
					DisplayString,
				acFan10Fault
					DisplayString,
				acFan11Fault
					DisplayString,
				acFan12Fault
					DisplayString,
				acFan13Fault
					DisplayString,
				acFan14Fault
					DisplayString,
				acFan15Fault
					DisplayString,
				acFan16Fault
					DisplayString,
				acACPowerFault
					DisplayString,
				acDCPowerFault
					DisplayString,
				acValve1Fault
					DisplayString,
				acValve2Fault
					DisplayString,
				acCommFault
					DisplayString,
				acWaterLeakAlarm
					DisplayString,
				acWaterLevelH
					DisplayString,
				acFilterTimeArrived
					DisplayString,
				acFanTimeArrived
					DisplayString,
				acValveTimeArrived
					DisplayString,
				acWaterPumpFault
					DisplayString,
				acShutdownAlarm
					DisplayString,
				acACCircuitBreaker
					DisplayString,
				acDCCircuitBreaker
					DisplayString,
				acSupplyTempSet
					DisplayString,
				acReturnTempSet
					DisplayString,
				acStaticPressureSet
					DisplayString
			 }

--     1.3.6.1.4.1.41475.3.1.5.8.1.1.1
-- 1.3.6.1.4.1.41475.3.1.5.8.1.1.1
-- 1.3.6.1.4.1.41475.3.1.4.7.1.1.1
-- 1.3.6.1.4.1.41475.3.1.4.7.1.1.1
		-- 1.3.6.1.4.1.41475.3.1.4.6.1.1.1
		acIndex OBJECT-TYPE
			SYNTAX Integer32 (1..9999)
			MAX-ACCESS read-only
			STATUS current
			DESCRIPTION
				"Description: The serial number, starting from 1"
			::= { acEntry 1 }

		
--   1.3.6.1.4.1.41475.3.1.4.7.1.1.2
-- 1.3.6.1.4.1.41475.3.1.4.7.1.1.2
		-- 1.3.6.1.4.1.41475.3.1.4.6.1.1.2
		acFanSpeed OBJECT-TYPE
			SYNTAX DisplayString
			UNITS "%"
			MAX-ACCESS read-only
			STATUS current
			DESCRIPTION
				"Description: Fan speed."
			::= { acEntry 2 }

		
--     1.3.6.1.4.1.41475.3.1.5.8.1.1.12
-- 1.3.6.1.4.1.41475.3.1.5.8.1.1.12
-- 1.3.6.1.4.1.41475.3.1.4.7.1.1.3
-- 1.3.6.1.4.1.41475.3.1.4.7.1.1.3
		-- 1.3.6.1.4.1.41475.3.1.4.6.1.1.3
		acWaterValveOpening OBJECT-TYPE
			SYNTAX DisplayString
			UNITS "%"
			MAX-ACCESS read-only
			STATUS current
			DESCRIPTION
				"Description: Valve opening degree"
			::= { acEntry 3 }

		
--     1.3.6.1.4.1.41475.3.1.5.8.1.1.4
-- 1.3.6.1.4.1.41475.3.1.5.8.1.1.4
-- 1.3.6.1.4.1.41475.3.1.4.7.1.1.4
-- 1.3.6.1.4.1.41475.3.1.4.7.1.1.4
		-- 1.3.6.1.4.1.41475.3.1.4.6.1.1.4
		acReturnTempUpper OBJECT-TYPE
			SYNTAX DisplayString
			UNITS "¡æ"
			MAX-ACCESS read-only
			STATUS current
			DESCRIPTION
				"Description: The upper part of the return air temperature."
			::= { acEntry 4 }

		
--     1.3.6.1.4.1.41475.3.1.5.8.1.1.6
-- 1.3.6.1.4.1.41475.3.1.5.8.1.1.6
-- 1.3.6.1.4.1.41475.3.1.4.7.1.1.5
-- 1.3.6.1.4.1.41475.3.1.4.7.1.1.5
		-- 1.3.6.1.4.1.41475.3.1.4.6.1.1.5
		acReturnTempCentral OBJECT-TYPE
			SYNTAX DisplayString
			UNITS "¡æ"
			MAX-ACCESS read-only
			STATUS current
			DESCRIPTION
				"Description: air temperature in central."
			::= { acEntry 5 }

		
--     1.3.6.1.4.1.41475.3.1.5.8.1.1.8
-- 1.3.6.1.4.1.41475.3.1.5.8.1.1.8
-- 1.3.6.1.4.1.41475.3.1.4.7.1.1.6
-- 1.3.6.1.4.1.41475.3.1.4.7.1.1.6
		-- 1.3.6.1.4.1.41475.3.1.4.6.1.1.6
		acReturnTempLower OBJECT-TYPE
			SYNTAX DisplayString
			UNITS "¡æ"
			MAX-ACCESS read-only
			STATUS current
			DESCRIPTION
				"Description: The lower part of the return air temperature."
			::= { acEntry 6 }

		
--     1.3.6.1.4.1.41475.3.1.5.8.1.1.9
-- 1.3.6.1.4.1.41475.3.1.5.8.1.1.9
-- 1.3.6.1.4.1.41475.3.1.4.7.1.1.7
-- 1.3.6.1.4.1.41475.3.1.4.7.1.1.7
		-- 1.3.6.1.4.1.41475.3.1.4.6.1.1.7
		acReturnHum OBJECT-TYPE
			SYNTAX DisplayString
			UNITS "%"
			MAX-ACCESS read-only
			STATUS current
			DESCRIPTION
				"Description: Return air humidity."
			::= { acEntry 7 }

		
--     1.3.6.1.4.1.41475.3.1.5.8.1.1.3
-- 1.3.6.1.4.1.41475.3.1.5.8.1.1.3
-- 1.3.6.1.4.1.41475.3.1.4.7.1.1.8
-- 1.3.6.1.4.1.41475.3.1.4.7.1.1.8
		-- 1.3.6.1.4.1.41475.3.1.4.6.1.1.8
		acSupplyTempUpper OBJECT-TYPE
			SYNTAX DisplayString
			UNITS "¡æ"
			MAX-ACCESS read-only
			STATUS current
			DESCRIPTION
				"Description: Upper air humidity."
			::= { acEntry 8 }

		
--     1.3.6.1.4.1.41475.3.1.5.8.1.1.5
-- 1.3.6.1.4.1.41475.3.1.5.8.1.1.5
-- 1.3.6.1.4.1.41475.3.1.4.7.1.1.9
-- 1.3.6.1.4.1.41475.3.1.4.7.1.1.9
		-- 1.3.6.1.4.1.41475.3.1.4.6.1.1.9
		acSupplyTempCentral OBJECT-TYPE
			SYNTAX DisplayString
			UNITS "¡æ"
			MAX-ACCESS read-only
			STATUS current
			DESCRIPTION
				"Description: Central air humidity."
			::= { acEntry 9 }

		
--     1.3.6.1.4.1.41475.3.1.5.8.1.1.7
-- 1.3.6.1.4.1.41475.3.1.5.8.1.1.7
-- 1.3.6.1.4.1.41475.3.1.4.7.1.1.10
-- 1.3.6.1.4.1.41475.3.1.4.7.1.1.10
		-- 1.3.6.1.4.1.41475.3.1.4.6.1.1.10
		acSupplyTempLower OBJECT-TYPE
			SYNTAX DisplayString
			UNITS "¡æ"
			MAX-ACCESS read-only
			STATUS current
			DESCRIPTION
				"Description: Lower air humidity."
			::= { acEntry 10 }

		
--     1.3.6.1.4.1.41475.3.1.5.8.1.1.13
-- 1.3.6.1.4.1.41475.3.1.5.8.1.1.13
-- 1.3.6.1.4.1.41475.3.1.4.7.1.1.11
-- 1.3.6.1.4.1.41475.3.1.4.7.1.1.11
		-- 1.3.6.1.4.1.41475.3.1.4.6.1.1.11
		acSupplyHum OBJECT-TYPE
			SYNTAX DisplayString
			UNITS "%"
			MAX-ACCESS read-only
			STATUS current
			DESCRIPTION
				"Description: Air humidity."
			::= { acEntry 11 }

		
--     1.3.6.1.4.1.41475.3.1.5.8.1.1.10
-- 1.3.6.1.4.1.41475.3.1.5.8.1.1.10
-- 1.3.6.1.4.1.41475.3.1.4.7.1.1.12
-- 1.3.6.1.4.1.41475.3.1.4.7.1.1.12
		-- 1.3.6.1.4.1.41475.3.1.4.6.1.1.12
		acSupplyWaterTemp OBJECT-TYPE
			SYNTAX DisplayString
			UNITS "¡æ"
			MAX-ACCESS read-only
			STATUS current
			DESCRIPTION
				"Description: Water temperature."
			::= { acEntry 12 }

		
--     1.3.6.1.4.1.41475.3.1.5.8.1.1.11
-- 1.3.6.1.4.1.41475.3.1.5.8.1.1.11
-- 1.3.6.1.4.1.41475.3.1.4.7.1.1.13
-- 1.3.6.1.4.1.41475.3.1.4.7.1.1.13
		-- 1.3.6.1.4.1.41475.3.1.4.6.1.1.13
		acReturnWaterTemp OBJECT-TYPE
			SYNTAX DisplayString
			UNITS "¡æ"
			MAX-ACCESS read-only
			STATUS current
			DESCRIPTION
				"Description: Return water temperature."
			::= { acEntry 13 }

		
--     1.3.6.1.4.1.41475.3.1.5.8.1.1.11
-- 1.3.6.1.4.1.41475.3.1.5.8.1.1.11
-- 1.3.6.1.4.1.41475.3.1.4.7.1.1.13
-- 1.3.6.1.4.1.41475.3.1.4.7.1.1.14
		-- 1.3.6.1.4.1.41475.3.1.4.6.1.1.14
		acSupplyWaterPressure OBJECT-TYPE
			SYNTAX DisplayString
			UNITS "Pa"
			MAX-ACCESS read-only
			STATUS current
			DESCRIPTION
				"Description: Supply water pressure."
			::= { acEntry 14 }

		
--     1.3.6.1.4.1.41475.3.1.5.8.1.1.11
-- 1.3.6.1.4.1.41475.3.1.5.8.1.1.11
-- 1.3.6.1.4.1.41475.3.1.4.7.1.1.13
-- 1.3.6.1.4.1.41475.3.1.4.7.1.1.15
		-- 1.3.6.1.4.1.41475.3.1.4.6.1.1.15
		acReturnWaterPressure OBJECT-TYPE
			SYNTAX DisplayString
			UNITS "Pa"
			MAX-ACCESS read-only
			STATUS current
			DESCRIPTION
				"Description: Return water pressure."
			::= { acEntry 15 }

		
--     1.3.6.1.4.1.41475.3.1.5.8.1.1.11
-- 1.3.6.1.4.1.41475.3.1.5.8.1.1.11
-- 1.3.6.1.4.1.41475.3.1.4.7.1.1.13
-- 1.3.6.1.4.1.41475.3.1.4.7.1.1.16
		-- 1.3.6.1.4.1.41475.3.1.4.6.1.1.16
		acWindDifferentialPressure OBJECT-TYPE
			SYNTAX DisplayString
			UNITS "Pa"
			MAX-ACCESS read-only
			STATUS current
			DESCRIPTION
				"Description: Wind differential pressure."
			::= { acEntry 16 }

		
--     1.3.6.1.4.1.41475.3.1.5.8.1.1.25
-- 1.3.6.1.4.1.41475.3.1.5.8.1.1.25
-- 1.3.6.1.4.1.41475.3.1.4.7.1.1.14
-- 1.3.6.1.4.1.41475.3.1.4.7.1.1.17
		-- 1.3.6.1.4.1.41475.3.1.4.6.1.1.17
		acRTempSensor1Fault OBJECT-TYPE
			SYNTAX DisplayString
			MAX-ACCESS read-only
			STATUS current
			DESCRIPTION
				"Description: Return air temperature sensor-1 failure.
				Reasons: For 30 seconds, the sensor-1 value is not within the normal range.
				Values: 0-ok, 1-fault"
			::= { acEntry 17 }

		
--     1.3.6.1.4.1.41475.3.1.5.8.1.1.25
-- 1.3.6.1.4.1.41475.3.1.5.8.1.1.25
-- 1.3.6.1.4.1.41475.3.1.4.7.1.1.15
-- 1.3.6.1.4.1.41475.3.1.4.7.1.1.18
		-- 1.3.6.1.4.1.41475.3.1.4.6.1.1.18
		acRTempSensor2Fault OBJECT-TYPE
			SYNTAX DisplayString
			MAX-ACCESS read-only
			STATUS current
			DESCRIPTION
				"Description: Return air temperature sensor-2 failure.
				Reasons: For 30 seconds, the sensor-2 value is not within the normal range.
				Values: 0-ok, 1-fault"
			::= { acEntry 18 }

		
--     1.3.6.1.4.1.41475.3.1.5.8.1.1.25
-- 1.3.6.1.4.1.41475.3.1.5.8.1.1.25
-- 1.3.6.1.4.1.41475.3.1.4.7.1.1.16
-- 1.3.6.1.4.1.41475.3.1.4.7.1.1.19
		-- 1.3.6.1.4.1.41475.3.1.4.6.1.1.19
		acRTempSensor3Fault OBJECT-TYPE
			SYNTAX DisplayString
			MAX-ACCESS read-only
			STATUS current
			DESCRIPTION
				"Description: Return air temperature sensor-3 failure.
				Reasons: For 30 seconds, the sensor-3 value is not within the normal range.
				Values: 0-ok, 1-fault"
			::= { acEntry 19 }

		
--     1.3.6.1.4.1.41475.3.1.5.8.1.1.27
-- 1.3.6.1.4.1.41475.3.1.5.8.1.1.27
-- 1.3.6.1.4.1.41475.3.1.4.7.1.1.17
-- 1.3.6.1.4.1.41475.3.1.4.7.1.1.20
		-- 1.3.6.1.4.1.41475.3.1.4.6.1.1.20
		acSTempSensor1Fault OBJECT-TYPE
			SYNTAX DisplayString
			MAX-ACCESS read-only
			STATUS current
			DESCRIPTION
				"Description: air temperature sensor-1 failure.
				Reasons: For 30 seconds, the sensor-1 value is not within the normal range.
				Values: 0-ok, 1-fault"
			::= { acEntry 20 }

		
--     1.3.6.1.4.1.41475.3.1.5.8.1.1.28
-- 1.3.6.1.4.1.41475.3.1.5.8.1.1.28
-- 1.3.6.1.4.1.41475.3.1.4.7.1.1.18
-- 1.3.6.1.4.1.41475.3.1.4.7.1.1.21
		-- 1.3.6.1.4.1.41475.3.1.4.6.1.1.21
		acSTempSensor2Fault OBJECT-TYPE
			SYNTAX DisplayString
			MAX-ACCESS read-only
			STATUS current
			DESCRIPTION
				"Description: air temperature sensor-2 failure.
				Reasons: For 30 seconds, the sensor-2 value is not within the normal range.
				Values: 0-ok, 1-fault"
			::= { acEntry 21 }

		
--     1.3.6.1.4.1.41475.3.1.5.8.1.1.29
-- 1.3.6.1.4.1.41475.3.1.5.8.1.1.29
-- 1.3.6.1.4.1.41475.3.1.4.7.1.1.19
-- 1.3.6.1.4.1.41475.3.1.4.7.1.1.22
		-- 1.3.6.1.4.1.41475.3.1.4.6.1.1.22
		acSTempSensor3Fault OBJECT-TYPE
			SYNTAX DisplayString
			MAX-ACCESS read-only
			STATUS current
			DESCRIPTION
				"Description: air temperature sensor-3 failure.
				Reasons: For 30 seconds, the sensor-3 value is not within the normal range.
				Values: 0-ok, 1-fault"
			::= { acEntry 22 }

		
--     1.3.6.1.4.1.41475.3.1.5.8.1.1.39
-- 1.3.6.1.4.1.41475.3.1.5.8.1.1.39
-- 1.3.6.1.4.1.41475.3.1.4.7.1.1.20
-- 1.3.6.1.4.1.41475.3.1.4.7.1.1.23
		-- 1.3.6.1.4.1.41475.3.1.4.6.1.1.23
		acRHumSensorFault OBJECT-TYPE
			SYNTAX DisplayString
			MAX-ACCESS read-only
			STATUS current
			DESCRIPTION
				"Description: Return air humidity sensor fault
				Reasons: For 30 seconds, the sensor value is not within the normal range.
				Values: 0-ok, 1-fault"
			::= { acEntry 23 }

		
--     1.3.6.1.4.1.41475.3.1.5.8.1.1.39
-- 1.3.6.1.4.1.41475.3.1.5.8.1.1.39
-- 1.3.6.1.4.1.41475.3.1.4.7.1.1.21
-- 1.3.6.1.4.1.41475.3.1.4.7.1.1.24
		-- 1.3.6.1.4.1.41475.3.1.4.6.1.1.24
		acSHumSensorFault OBJECT-TYPE
			SYNTAX DisplayString
			MAX-ACCESS read-only
			STATUS current
			DESCRIPTION
				"Description: air humidity sensor fault
				Reasons: For 30 seconds, the sensor value is not within the normal range.
				Values: 0-ok, 1-fault"
			::= { acEntry 24 }

		
--     1.3.6.1.4.1.41475.3.1.5.8.1.1.31
-- 1.3.6.1.4.1.41475.3.1.5.8.1.1.31
-- 1.3.6.1.4.1.41475.3.1.4.7.1.1.22
-- 1.3.6.1.4.1.41475.3.1.4.7.1.1.25
		-- 1.3.6.1.4.1.41475.3.1.4.6.1.1.25
		acFan1Fault OBJECT-TYPE
			SYNTAX DisplayString
			MAX-ACCESS read-only
			STATUS current
			DESCRIPTION
				"Description: Fan-1 failure
				Reasons: For 30 seconds, the fan is detected at frequencies below ¡®set-point' or?for 10 seconds,?the fan sensor feedback failure.
				Values: 0-ok, 1-fault"
			::= { acEntry 25 }

		
--     1.3.6.1.4.1.41475.3.1.5.8.1.1.31
-- 1.3.6.1.4.1.41475.3.1.5.8.1.1.31
-- 1.3.6.1.4.1.41475.3.1.4.7.1.1.23
-- 1.3.6.1.4.1.41475.3.1.4.7.1.1.26
		-- 1.3.6.1.4.1.41475.3.1.4.6.1.1.26
		acFan2Fault OBJECT-TYPE
			SYNTAX DisplayString
			MAX-ACCESS read-only
			STATUS current
			DESCRIPTION
				"Description: Fan-2 failure
				Reasons: For 30 seconds, the fan is detected at frequencies below ¡®set-point' or?for 10 seconds,?the fan sensor feedback failure.
				Values: 0-ok, 1-fault"
			::= { acEntry 26 }

		
--     1.3.6.1.4.1.41475.3.1.5.8.1.1.31
-- 1.3.6.1.4.1.41475.3.1.5.8.1.1.31
-- 1.3.6.1.4.1.41475.3.1.4.7.1.1.24
-- 1.3.6.1.4.1.41475.3.1.4.7.1.1.27
		-- 1.3.6.1.4.1.41475.3.1.4.6.1.1.27
		acFan3Fault OBJECT-TYPE
			SYNTAX DisplayString
			MAX-ACCESS read-only
			STATUS current
			DESCRIPTION
				"Description: Fan-3 failure
				Reasons: For 30 seconds, the fan is detected at frequencies below ¡®set-point' or?for 10 seconds,?the fan sensor feedback failure.
				Values: 0-ok, 1-fault"
			::= { acEntry 27 }

		
--     1.3.6.1.4.1.41475.3.1.5.8.1.1.31
-- 1.3.6.1.4.1.41475.3.1.5.8.1.1.31
-- 1.3.6.1.4.1.41475.3.1.4.7.1.1.25
-- 1.3.6.1.4.1.41475.3.1.4.7.1.1.28
		-- 1.3.6.1.4.1.41475.3.1.4.6.1.1.28
		acFan4Fault OBJECT-TYPE
			SYNTAX DisplayString
			MAX-ACCESS read-only
			STATUS current
			DESCRIPTION
				"Description: Fan-4 failure
				Reasons: For 30 seconds, the fan is detected at frequencies below ¡®set-point' or?for 10 seconds,?the fan sensor feedback failure.
				Values: 0-ok, 1-fault"
			::= { acEntry 28 }

		
--     1.3.6.1.4.1.41475.3.1.5.8.1.1.31
-- 1.3.6.1.4.1.41475.3.1.5.8.1.1.31
-- 1.3.6.1.4.1.41475.3.1.4.7.1.1.26
-- 1.3.6.1.4.1.41475.3.1.4.7.1.1.29
		-- 1.3.6.1.4.1.41475.3.1.4.6.1.1.29
		acFan5Fault OBJECT-TYPE
			SYNTAX DisplayString
			MAX-ACCESS read-only
			STATUS current
			DESCRIPTION
				"Description: Fan-5 failure
				Reasons: For 30 seconds, the fan is detected at frequencies below ¡®set-point' or?for 10 seconds,?the fan sensor feedback failure.
				Values: 0-ok, 1-fault"
			::= { acEntry 29 }

		
--     1.3.6.1.4.1.41475.3.1.5.8.1.1.31
-- 1.3.6.1.4.1.41475.3.1.5.8.1.1.31
-- 1.3.6.1.4.1.41475.3.1.4.7.1.1.27
-- 1.3.6.1.4.1.41475.3.1.4.7.1.1.30
		-- 1.3.6.1.4.1.41475.3.1.4.6.1.1.30
		acFan6Fault OBJECT-TYPE
			SYNTAX DisplayString
			MAX-ACCESS read-only
			STATUS current
			DESCRIPTION
				"Description: Fan-6 failure
				Reasons: For 30 seconds, the fan is detected at frequencies below ¡®set-point' or?for 10 seconds,?the fan sensor feedback failure.
				Values: 0-ok, 1-fault"
			::= { acEntry 30 }

		
--     1.3.6.1.4.1.41475.3.1.5.8.1.1.31
-- 1.3.6.1.4.1.41475.3.1.5.8.1.1.31
-- 1.3.6.1.4.1.41475.3.1.4.7.1.1.28
-- 1.3.6.1.4.1.41475.3.1.4.7.1.1.31
		-- 1.3.6.1.4.1.41475.3.1.4.6.1.1.31
		acFan7Fault OBJECT-TYPE
			SYNTAX DisplayString
			MAX-ACCESS read-only
			STATUS current
			DESCRIPTION
				"Description: Fan-7 failure
				Reasons: For 30 seconds, the fan is detected at frequencies below ¡®set-point' or?for 10 seconds,?the fan sensor feedback failure.
				Values: 0-ok, 1-fault"
			::= { acEntry 31 }

		
--     1.3.6.1.4.1.41475.3.1.5.8.1.1.31
-- 1.3.6.1.4.1.41475.3.1.5.8.1.1.31
-- 1.3.6.1.4.1.41475.3.1.4.7.1.1.29
-- 1.3.6.1.4.1.41475.3.1.4.7.1.1.32
		-- 1.3.6.1.4.1.41475.3.1.4.6.1.1.32
		acFan8Fault OBJECT-TYPE
			SYNTAX DisplayString
			MAX-ACCESS read-only
			STATUS current
			DESCRIPTION
				"Description: Fan-8 failure
				Reasons: For 30 seconds, the fan is detected at frequencies below ¡®set-point' or?for 10 seconds,?the fan sensor feedback failure.
				Values: 0-ok, 1-fault"
			::= { acEntry 32 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.33
		acFan9Fault OBJECT-TYPE
			SYNTAX DisplayString
			MAX-ACCESS read-only
			STATUS current
			DESCRIPTION
				"Description: Fan-9 failure
				Reasons: For 30 seconds, the fan is detected at frequencies below ¡®set-point' or?for 10 seconds,?the fan sensor feedback failure.
				Values: 0-ok, 1-fault"
			::= { acEntry 33 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.34
		acFan10Fault OBJECT-TYPE
			SYNTAX DisplayString
			MAX-ACCESS read-only
			STATUS current
			DESCRIPTION
				"Description: Fan-10 failure
				Reasons: For 30 seconds, the fan is detected at frequencies below ¡®set-point' or?for 10 seconds,?the fan sensor feedback failure.
				Values: 0-ok, 1-fault"
			::= { acEntry 34 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.35
		acFan11Fault OBJECT-TYPE
			SYNTAX DisplayString
			MAX-ACCESS read-only
			STATUS current
			DESCRIPTION
				"Description: Fan-11 failure
				Reasons: For 30 seconds, the fan is detected at frequencies below ¡®set-point' or?for 10 seconds,?the fan sensor feedback failure.
				Values: 0-ok, 1-fault"
			::= { acEntry 35 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.36
		acFan12Fault OBJECT-TYPE
			SYNTAX DisplayString
			MAX-ACCESS read-only
			STATUS current
			DESCRIPTION
				"Description: Fan-12 failure
				Reasons: For 30 seconds, the fan is detected at frequencies below ¡®set-point' or?for 10 seconds,?the fan sensor feedback failure.
				Values: 0-ok, 1-fault"
			::= { acEntry 36 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.37
		acFan13Fault OBJECT-TYPE
			SYNTAX DisplayString
			MAX-ACCESS read-only
			STATUS current
			DESCRIPTION
				"Description: Fan-13 failure
				Reasons: For 30 seconds, the fan is detected at frequencies below ¡®set-point' or?for 10 seconds,?the fan sensor feedback failure.
				Values: 0-ok, 1-fault"
			::= { acEntry 37 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.38
		acFan14Fault OBJECT-TYPE
			SYNTAX DisplayString
			MAX-ACCESS read-only
			STATUS current
			DESCRIPTION
				"Description: Fan-14 failure
				Reasons: For 30 seconds, the fan is detected at frequencies below ¡®set-point' or?for 10 seconds,?the fan sensor feedback failure.
				Values: 0-ok, 1-fault"
			::= { acEntry 38 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.39
		acFan15Fault OBJECT-TYPE
			SYNTAX DisplayString
			MAX-ACCESS read-only
			STATUS current
			DESCRIPTION
				"Description: Fan-15 failure
				Reasons: For 30 seconds, the fan is detected at frequencies below ¡®set-point' or?for 10 seconds,?the fan sensor feedback failure.
				Values: 0-ok, 1-fault"
			::= { acEntry 39 }

		
--     1.3.6.1.4.1.41475.3.1.5.8.1.1.31
-- 1.3.6.1.4.1.41475.3.1.5.8.1.1.31
-- 1.3.6.1.4.1.41475.3.1.4.7.1.1.30
-- 1.3.6.1.4.1.41475.3.1.4.7.1.1.33
		-- 1.3.6.1.4.1.41475.3.1.4.6.1.1.40
		acFan16Fault OBJECT-TYPE
			SYNTAX DisplayString
			MAX-ACCESS read-only
			STATUS current
			DESCRIPTION
				"Description: Fan-16 failure
				Reasons: For 30 seconds, the fan is detected at frequencies below ¡®set-point' or?for 10 seconds,?the fan sensor feedback failure.
				Values: 0-ok, 1-fault"
			::= { acEntry 40 }

		
--     1.3.6.1.4.1.41475.3.1.5.8.1.1.41
-- 1.3.6.1.4.1.41475.3.1.5.8.1.1.41
-- 1.3.6.1.4.1.41475.3.1.4.7.1.1.31
-- 1.3.6.1.4.1.41475.3.1.4.7.1.1.34
		-- 1.3.6.1.4.1.41475.3.1.4.6.1.1.41
		acACPowerFault OBJECT-TYPE
			SYNTAX DisplayString
			MAX-ACCESS read-only
			STATUS current
			DESCRIPTION
				"Description: AC power failure
				Reasons: For 5 seconds, and the AC power supply abnormality is detected.
				Values: 0-ok, 1-fault"
			::= { acEntry 41 }

		
--     1.3.6.1.4.1.41475.3.1.5.8.1.1.41
-- 1.3.6.1.4.1.41475.3.1.5.8.1.1.41
-- 1.3.6.1.4.1.41475.3.1.4.7.1.1.32
-- 1.3.6.1.4.1.41475.3.1.4.7.1.1.35
		-- 1.3.6.1.4.1.41475.3.1.4.6.1.1.42
		acDCPowerFault OBJECT-TYPE
			SYNTAX DisplayString
			MAX-ACCESS read-only
			STATUS current
			DESCRIPTION
				"Description: DC power failure
				Reasons: For 5 seconds, and the DC power supply abnormality is detected.
				Values: 0-ok, 1-fault"
			::= { acEntry 42 }

		
--     1.3.6.1.4.1.41475.3.1.5.8.1.1.41
-- 1.3.6.1.4.1.41475.3.1.5.8.1.1.41
-- 1.3.6.1.4.1.41475.3.1.4.7.1.1.33
-- 1.3.6.1.4.1.41475.3.1.4.7.1.1.36
		-- 1.3.6.1.4.1.41475.3.1.4.6.1.1.43
		acValve1Fault OBJECT-TYPE
			SYNTAX DisplayString
			MAX-ACCESS read-only
			STATUS current
			DESCRIPTION
				"Description: Valve-1 failure
				Reasons: For 3 minutes, the water valve opening is more than 20% higher than the actual water valve
				Values: 0-ok, 1-fault"
			::= { acEntry 43 }

		
--     1.3.6.1.4.1.41475.3.1.5.8.1.1.41
-- 1.3.6.1.4.1.41475.3.1.5.8.1.1.41
-- 1.3.6.1.4.1.41475.3.1.4.7.1.1.34
-- 1.3.6.1.4.1.41475.3.1.4.7.1.1.37
		-- 1.3.6.1.4.1.41475.3.1.4.6.1.1.44
		acValve2Fault OBJECT-TYPE
			SYNTAX DisplayString
			MAX-ACCESS read-only
			STATUS current
			DESCRIPTION
				"Description: Valve-2 failure
				Reasons: For 3 minutes, the water valve opening is more than 20% higher than the actual water valve
				Values: 0-ok, 1-fault"
			::= { acEntry 44 }

		
--     1.3.6.1.4.1.41475.3.1.5.8.1.1.41
-- 1.3.6.1.4.1.41475.3.1.5.8.1.1.41
-- 1.3.6.1.4.1.41475.3.1.4.7.1.1.35
-- 1.3.6.1.4.1.41475.3.1.4.7.1.1.38
		-- 1.3.6.1.4.1.41475.3.1.4.6.1.1.45
		acCommFault OBJECT-TYPE
			SYNTAX DisplayString
			MAX-ACCESS read-only
			STATUS current
			DESCRIPTION
				"Description: Communication fault
				Reasons: When the Group-control is open, and the detection to the host is not online.
				Values: 0-ok, 1-fault"
			::= { acEntry 45 }

		
--     1.3.6.1.4.1.41475.3.1.5.8.1.1.41
-- 1.3.6.1.4.1.41475.3.1.5.8.1.1.41
-- 1.3.6.1.4.1.41475.3.1.4.7.1.1.36
-- 1.3.6.1.4.1.41475.3.1.4.7.1.1.39
		-- 1.3.6.1.4.1.41475.3.1.4.6.1.1.46
		acWaterLeakAlarm OBJECT-TYPE
			SYNTAX DisplayString
			MAX-ACCESS read-only
			STATUS current
			DESCRIPTION
				"Description: Water Leakage alarm
				Reasons: For 5 seconds, found Water Leakage alarm.
				Values: 0-ok, 1-Alarm"
			::= { acEntry 46 }

		
--     1.3.6.1.4.1.41475.3.1.5.8.1.1.41
-- 1.3.6.1.4.1.41475.3.1.5.8.1.1.41
-- 1.3.6.1.4.1.41475.3.1.4.7.1.1.37
-- 1.3.6.1.4.1.41475.3.1.4.7.1.1.40
		-- 1.3.6.1.4.1.41475.3.1.4.6.1.1.47
		acWaterLevelH OBJECT-TYPE
			SYNTAX DisplayString
			MAX-ACCESS read-only
			STATUS current
			DESCRIPTION
				"Description: Water level is too high
				Reasons: For 5 seconds, detected in high water level
				Values: 0-ok, 1-Alarm"
			::= { acEntry 47 }

		
--     1.3.6.1.4.1.41475.3.1.5.8.1.1.41
-- 1.3.6.1.4.1.41475.3.1.5.8.1.1.41
-- 1.3.6.1.4.1.41475.3.1.4.7.1.1.38
-- 1.3.6.1.4.1.41475.3.1.4.7.1.1.41
		-- 1.3.6.1.4.1.41475.3.1.4.6.1.1.48
		acFilterTimeArrived OBJECT-TYPE
			SYNTAX DisplayString
			MAX-ACCESS read-only
			STATUS current
			DESCRIPTION
				"Description: Filter maintenance time has arrived.
				Reasons: Beyond the set-time
				Values: 0-ok, 1-Alarm"
			::= { acEntry 48 }

		
--     1.3.6.1.4.1.41475.3.1.5.8.1.1.41
-- 1.3.6.1.4.1.41475.3.1.5.8.1.1.41
-- 1.3.6.1.4.1.41475.3.1.4.7.1.1.39
-- 1.3.6.1.4.1.41475.3.1.4.7.1.1.42
		-- 1.3.6.1.4.1.41475.3.1.4.6.1.1.49
		acFanTimeArrived OBJECT-TYPE
			SYNTAX DisplayString
			MAX-ACCESS read-only
			STATUS current
			DESCRIPTION
				"Description: Fan maintenance time has arrived.
				Reasons: Beyond the set-time
				Values: 0-ok, 1-Alarm"
			::= { acEntry 49 }

		
--     1.3.6.1.4.1.41475.3.1.5.8.1.1.41
-- 1.3.6.1.4.1.41475.3.1.5.8.1.1.41
-- 1.3.6.1.4.1.41475.3.1.4.7.1.1.40
-- 1.3.6.1.4.1.41475.3.1.4.7.1.1.43
		-- 1.3.6.1.4.1.41475.3.1.4.6.1.1.50
		acValveTimeArrived OBJECT-TYPE
			SYNTAX DisplayString
			MAX-ACCESS read-only
			STATUS current
			DESCRIPTION
				"Description: Valve maintenance time has arrived.
				Reasons: Beyond the set-time
				Values: 0-ok, 1-Alarm"
			::= { acEntry 50 }

		
--     1.3.6.1.4.1.41475.3.1.5.8.1.1.41
-- 1.3.6.1.4.1.41475.3.1.5.8.1.1.41
-- 1.3.6.1.4.1.41475.3.1.4.7.1.1.41
-- 1.3.6.1.4.1.41475.3.1.4.7.1.1.44
		-- 1.3.6.1.4.1.41475.3.1.4.6.1.1.51
		acWaterPumpFault OBJECT-TYPE
			SYNTAX DisplayString
			MAX-ACCESS read-only
			STATUS current
			DESCRIPTION
				"Description: Water pump Fault
				Reasons: For 30 seconds, to detect water pump failure.
				Values: 0-ok, 1-fault"
			::= { acEntry 51 }

		
--     1.3.6.1.4.1.41475.3.1.5.8.1.1.41
-- 1.3.6.1.4.1.41475.3.1.5.8.1.1.41
-- 1.3.6.1.4.1.41475.3.1.4.7.1.1.42
-- 1.3.6.1.4.1.41475.3.1.4.7.1.1.45
		-- 1.3.6.1.4.1.41475.3.1.4.6.1.1.52
		acShutdownAlarm OBJECT-TYPE
			SYNTAX DisplayString
			MAX-ACCESS read-only
			STATUS current
			DESCRIPTION
				"Description: Shutdown alarm
				Values: 0-ok, 1-shutdown(alarm)"
			::= { acEntry 52 }

		
--     1.3.6.1.4.1.41475.3.1.5.8.1.1.41
-- 1.3.6.1.4.1.41475.3.1.5.8.1.1.41
-- 1.3.6.1.4.1.41475.3.1.4.7.1.1.43
-- 1.3.6.1.4.1.41475.3.1.4.7.1.1.46
		-- 1.3.6.1.4.1.41475.3.1.4.6.1.1.53
		acACCircuitBreaker OBJECT-TYPE
			SYNTAX DisplayString
			MAX-ACCESS read-only
			STATUS current
			DESCRIPTION
				"Description: the state of AC circuit breaker.
				Values: 0-ok, 1-open(Alarm)"
			::= { acEntry 53 }

		
--     1.3.6.1.4.1.41475.3.1.5.8.1.1.41
-- 1.3.6.1.4.1.41475.3.1.5.8.1.1.41
-- 1.3.6.1.4.1.41475.3.1.4.7.1.1.44
-- 1.3.6.1.4.1.41475.3.1.4.7.1.1.47
		-- 1.3.6.1.4.1.41475.3.1.4.6.1.1.54
		acDCCircuitBreaker OBJECT-TYPE
			SYNTAX DisplayString
			MAX-ACCESS read-only
			STATUS current
			DESCRIPTION
				"Description: the state of DC circuit breaker.
				Values: 0-ok, 1-open(Alarm)"
			::= { acEntry 54 }

		
--     1.3.6.1.4.1.41475.3.1.5.8.1.1.4
-- 1.3.6.1.4.1.41475.3.1.5.8.1.1.4
-- 1.3.6.1.4.1.41475.3.1.4.7.1.1.4
-- 1.3.6.1.4.1.41475.3.1.4.7.1.1.4
		-- 1.3.6.1.4.1.41475.3.1.4.6.1.1.55
		acSupplyTempSet OBJECT-TYPE
			SYNTAX DisplayString
			UNITS "¡æ"
			MAX-ACCESS read-only
			STATUS current
			DESCRIPTION
				"Description: Air supply temperature setting"
			::= { acEntry 55 }

		
--     1.3.6.1.4.1.41475.3.1.5.8.1.1.6
-- 1.3.6.1.4.1.41475.3.1.5.8.1.1.6
-- 1.3.6.1.4.1.41475.3.1.4.7.1.1.5
-- 1.3.6.1.4.1.41475.3.1.4.7.1.1.5
		-- 1.3.6.1.4.1.41475.3.1.4.6.1.1.56
		acReturnTempSet OBJECT-TYPE
			SYNTAX DisplayString
			UNITS "¡æ"
			MAX-ACCESS read-only
			STATUS current
			DESCRIPTION
				"Description: Air return temperature setting"
			::= { acEntry 56 }

		
--     1.3.6.1.4.1.41475.3.1.5.8.1.1.8
-- 1.3.6.1.4.1.41475.3.1.5.8.1.1.8
-- 1.3.6.1.4.1.41475.3.1.4.7.1.1.6
-- 1.3.6.1.4.1.41475.3.1.4.7.1.1.6
		-- 1.3.6.1.4.1.41475.3.1.4.6.1.1.57
		acStaticPressureSet OBJECT-TYPE
			SYNTAX DisplayString
			UNITS "Pa"
			MAX-ACCESS read-only
			STATUS current
			DESCRIPTION
				"Description: static pressure setting."
			::= { acEntry 57 }

		
--     1.3.6.1.4.1.41475.3.1.5.9
-- 1.3.6.1.4.1.41475.3.1.5.9
-- 1.3.6.1.4.1.41475.3.1.4.8
-- 1.3.6.1.4.1.41475.3.1.4.8
		-- 1.3.6.1.4.1.41475.3.1.4.7
		envTH OBJECT IDENTIFIER ::= { tmdcMonObjects 7 }

		
--     1.3.6.1.4.1.41475.3.1.5.9.1
-- 1.3.6.1.4.1.41475.3.1.5.9.1
-- 1.3.6.1.4.1.41475.3.1.4.8.1
-- 1.3.6.1.4.1.41475.3.1.4.8.1
		-- 1.3.6.1.4.1.41475.3.1.4.7.1
		envTHTable OBJECT-TYPE
			SYNTAX SEQUENCE OF EnvTHEntry
			MAX-ACCESS not-accessible
			STATUS current
			DESCRIPTION
				"Description."
			::= { envTH 1 }

		
--     1.3.6.1.4.1.41475.3.1.5.9.1.1
-- 1.3.6.1.4.1.41475.3.1.5.9.1.1
-- 1.3.6.1.4.1.41475.3.1.4.8.1.1
-- 1.3.6.1.4.1.41475.3.1.4.8.1.1
		-- 1.3.6.1.4.1.41475.3.1.4.7.1.1
		envTHEntry OBJECT-TYPE
			SYNTAX EnvTHEntry
			MAX-ACCESS not-accessible
			STATUS current
			DESCRIPTION
				"Description."
			INDEX { envRackIndex }
			::= { envTHTable 1 }

		
		EnvTHEntry ::=
			SEQUENCE { 
				envRackIndex
					Integer32,
				envRackLabel
					DisplayString,
				envCoolUpTemp
					DisplayString,
				envCoolUpHum
					DisplayString,
				envCoolMidTemp
					DisplayString,
				envCoolMidHum
					DisplayString,
				envCoolDownTemp
					DisplayString,
				envCoolDownHum
					DisplayString,
				envHotUpTemp
					DisplayString,
				envHotUpHum
					DisplayString,
				envHotMidTemp
					DisplayString,
				envHotMidHum
					DisplayString,
				envHotDownTemp
					DisplayString,
				envHotDownHum
					DisplayString
			 }

--     1.3.6.1.4.1.41475.3.1.5.9.1.1.1
-- 1.3.6.1.4.1.41475.3.1.5.9.1.1.1
-- 1.3.6.1.4.1.41475.3.1.4.8.1.1.1
-- 1.3.6.1.4.1.41475.3.1.4.8.1.1.1
		-- 1.3.6.1.4.1.41475.3.1.4.7.1.1.1
		envRackIndex OBJECT-TYPE
			SYNTAX Integer32 (1..9999)
			MAX-ACCESS read-only
			STATUS current
			DESCRIPTION
				"Description: The serial number, starting from 1"
			::= { envTHEntry 1 }

		
--   1.3.6.1.4.1.41475.3.1.4.8.1.1.2
-- 1.3.6.1.4.1.41475.3.1.4.8.1.1.2
		-- 1.3.6.1.4.1.41475.3.1.4.7.1.1.2
		envRackLabel OBJECT-TYPE
			SYNTAX DisplayString
			MAX-ACCESS read-only
			STATUS current
			DESCRIPTION
				"Description."
			::= { envTHEntry 2 }

		
--     1.3.6.1.4.1.41475.3.1.5.9.1.1.2
-- 1.3.6.1.4.1.41475.3.1.5.9.1.1.2
-- 1.3.6.1.4.1.41475.3.1.4.8.1.1.3
-- 1.3.6.1.4.1.41475.3.1.4.8.1.1.3
		-- 1.3.6.1.4.1.41475.3.1.4.7.1.1.3
		envCoolUpTemp OBJECT-TYPE
			SYNTAX DisplayString
			UNITS "¡æ"
			MAX-ACCESS read-only
			STATUS current
			DESCRIPTION
				"Description: The cooling channel, upper, temperature"
			::= { envTHEntry 3 }

		
--     1.3.6.1.4.1.41475.3.1.5.9.1.1.3
-- 1.3.6.1.4.1.41475.3.1.5.9.1.1.3
-- 1.3.6.1.4.1.41475.3.1.4.8.1.1.4
-- 1.3.6.1.4.1.41475.3.1.4.8.1.1.4
		-- 1.3.6.1.4.1.41475.3.1.4.7.1.1.4
		envCoolUpHum OBJECT-TYPE
			SYNTAX DisplayString
			UNITS "%"
			MAX-ACCESS read-only
			STATUS current
			DESCRIPTION
				"Description: The cooling channel, upper, humidity"
			::= { envTHEntry 4 }

		
--     1.3.6.1.4.1.41475.3.1.5.9.1.1.4
-- 1.3.6.1.4.1.41475.3.1.5.9.1.1.4
-- 1.3.6.1.4.1.41475.3.1.4.8.1.1.7
-- 1.3.6.1.4.1.41475.3.1.4.8.1.1.7
		-- 1.3.6.1.4.1.41475.3.1.4.7.1.1.5
		envCoolMidTemp OBJECT-TYPE
			SYNTAX DisplayString
			UNITS "¡æ"
			MAX-ACCESS read-only
			STATUS current
			DESCRIPTION
				"Description: The cooling channel, middle, temperature"
			::= { envTHEntry 5 }

		
--     1.3.6.1.4.1.41475.3.1.5.9.1.1.5
-- 1.3.6.1.4.1.41475.3.1.5.9.1.1.5
-- 1.3.6.1.4.1.41475.3.1.4.8.1.1.8
-- 1.3.6.1.4.1.41475.3.1.4.8.1.1.8
		-- 1.3.6.1.4.1.41475.3.1.4.7.1.1.6
		envCoolMidHum OBJECT-TYPE
			SYNTAX DisplayString
			UNITS "%"
			MAX-ACCESS read-only
			STATUS current
			DESCRIPTION
				"Description: The cooling channel, middle, humidity"
			::= { envTHEntry 6 }

		
--     1.3.6.1.4.1.41475.3.1.5.9.1.1.6
-- 1.3.6.1.4.1.41475.3.1.5.9.1.1.6
-- 1.3.6.1.4.1.41475.3.1.4.8.1.1.11
-- 1.3.6.1.4.1.41475.3.1.4.8.1.1.11
		-- 1.3.6.1.4.1.41475.3.1.4.7.1.1.7
		envCoolDownTemp OBJECT-TYPE
			SYNTAX DisplayString
			UNITS "¡æ"
			MAX-ACCESS read-only
			STATUS current
			DESCRIPTION
				"Description: The cooling channel, down, temperature"
			::= { envTHEntry 7 }

		
--     1.3.6.1.4.1.41475.3.1.5.9.1.1.7
-- 1.3.6.1.4.1.41475.3.1.5.9.1.1.7
-- 1.3.6.1.4.1.41475.3.1.4.8.1.1.12
-- 1.3.6.1.4.1.41475.3.1.4.8.1.1.12
		-- 1.3.6.1.4.1.41475.3.1.4.7.1.1.8
		envCoolDownHum OBJECT-TYPE
			SYNTAX DisplayString
			UNITS "%"
			MAX-ACCESS read-only
			STATUS current
			DESCRIPTION
				"Description: The cooling channel, down, humidity"
			::= { envTHEntry 8 }

		
--     1.3.6.1.4.1.41475.3.1.5.9.1.1.8
-- 1.3.6.1.4.1.41475.3.1.5.9.1.1.8
-- 1.3.6.1.4.1.41475.3.1.4.8.1.1.15
-- 1.3.6.1.4.1.41475.3.1.4.8.1.1.15
		-- 1.3.6.1.4.1.41475.3.1.4.7.1.1.9
		envHotUpTemp OBJECT-TYPE
			SYNTAX DisplayString
			UNITS "¡æ"
			MAX-ACCESS read-only
			STATUS current
			DESCRIPTION
				"Description: The Hot channel, up, temperature"
			::= { envTHEntry 9 }

		
--     1.3.6.1.4.1.41475.3.1.5.9.1.1.9
-- 1.3.6.1.4.1.41475.3.1.5.9.1.1.9
-- 1.3.6.1.4.1.41475.3.1.4.8.1.1.16
-- 1.3.6.1.4.1.41475.3.1.4.8.1.1.16
		-- 1.3.6.1.4.1.41475.3.1.4.7.1.1.10
		envHotUpHum OBJECT-TYPE
			SYNTAX DisplayString
			UNITS "%"
			MAX-ACCESS read-only
			STATUS current
			DESCRIPTION
				"Description: The Hot channel, up, humidity"
			::= { envTHEntry 10 }

		
--     1.3.6.1.4.1.41475.3.1.5.9.1.1.10
-- 1.3.6.1.4.1.41475.3.1.5.9.1.1.10
-- 1.3.6.1.4.1.41475.3.1.4.8.1.1.19
-- 1.3.6.1.4.1.41475.3.1.4.8.1.1.19
		-- 1.3.6.1.4.1.41475.3.1.4.7.1.1.11
		envHotMidTemp OBJECT-TYPE
			SYNTAX DisplayString
			UNITS "¡æ"
			MAX-ACCESS read-only
			STATUS current
			DESCRIPTION
				"Description: The Hot channel, middle, temperature"
			::= { envTHEntry 11 }

		
--     1.3.6.1.4.1.41475.3.1.5.9.1.1.11
-- 1.3.6.1.4.1.41475.3.1.5.9.1.1.11
-- 1.3.6.1.4.1.41475.3.1.4.8.1.1.20
-- 1.3.6.1.4.1.41475.3.1.4.8.1.1.20
		-- 1.3.6.1.4.1.41475.3.1.4.7.1.1.12
		envHotMidHum OBJECT-TYPE
			SYNTAX DisplayString
			UNITS "%"
			MAX-ACCESS read-only
			STATUS current
			DESCRIPTION
				"Description: The Hot channel, middle, humidity"
			::= { envTHEntry 12 }

		
--     1.3.6.1.4.1.41475.3.1.5.9.1.1.12
-- 1.3.6.1.4.1.41475.3.1.5.9.1.1.12
-- 1.3.6.1.4.1.41475.3.1.4.8.1.1.23
-- 1.3.6.1.4.1.41475.3.1.4.8.1.1.23
		-- 1.3.6.1.4.1.41475.3.1.4.7.1.1.13
		envHotDownTemp OBJECT-TYPE
			SYNTAX DisplayString
			UNITS "¡æ"
			MAX-ACCESS read-only
			STATUS current
			DESCRIPTION
				"Description: The Hot channel, down, temperature"
			::= { envTHEntry 13 }

		
--     1.3.6.1.4.1.41475.3.1.5.9.1.1.13
-- 1.3.6.1.4.1.41475.3.1.5.9.1.1.13
-- 1.3.6.1.4.1.41475.3.1.4.8.1.1.24
-- 1.3.6.1.4.1.41475.3.1.4.8.1.1.24
		-- 1.3.6.1.4.1.41475.3.1.4.7.1.1.14
		envHotDownHum OBJECT-TYPE
			SYNTAX DisplayString
			UNITS "%"
			MAX-ACCESS read-only
			STATUS current
			DESCRIPTION
				"Description: The Hot channel, down, humidity"
			::= { envTHEntry 14 }

		
--     1.3.6.1.4.1.41475.3.1.5.10
-- 1.3.6.1.4.1.41475.3.1.5.10
-- 1.3.6.1.4.1.41475.3.1.4.9
-- 1.3.6.1.4.1.41475.3.1.4.9
		-- 1.3.6.1.4.1.41475.3.1.4.8
		waterLeakage OBJECT IDENTIFIER ::= { tmdcMonObjects 8 }

		
--     1.3.6.1.4.1.41475.3.1.5.10.1
-- 1.3.6.1.4.1.41475.3.1.5.10.1
-- 1.3.6.1.4.1.41475.3.1.4.9.1
-- 1.3.6.1.4.1.41475.3.1.4.9.1
		-- 1.3.6.1.4.1.41475.3.1.4.8.1
		waterAllAround OBJECT-TYPE
			SYNTAX DisplayString
			MAX-ACCESS read-only
			STATUS current
			DESCRIPTION
				"Description: Water leakage around.
				Values: 0-ok, 1-Alarm"
			::= { waterLeakage 1 }

		
--     1.3.6.1.4.1.41475.3.1.5.10.2
-- 1.3.6.1.4.1.41475.3.1.5.10.2
-- 1.3.6.1.4.1.41475.3.1.4.9.3
-- 1.3.6.1.4.1.41475.3.1.4.9.3
		-- 1.3.6.1.4.1.41475.3.1.4.8.2
		waterAllocationUnit OBJECT-TYPE
			SYNTAX DisplayString
			MAX-ACCESS read-only
			STATUS current
			DESCRIPTION
				"Description: Water allocation unit found Water Leakage.
				Values: 0-ok, 1-Alarm"
			::= { waterLeakage 2 }

		
--     1.3.6.1.4.1.41475.3.1.5.11
-- 1.3.6.1.4.1.41475.3.1.5.11
-- 1.3.6.1.4.1.41475.3.1.4.10
-- 1.3.6.1.4.1.41475.3.1.4.10
		-- 1.3.6.1.4.1.41475.3.1.4.9
		vesda OBJECT IDENTIFIER ::= { tmdcMonObjects 9 }

		
--     1.3.6.1.4.1.41475.3.1.5.11.2
-- 1.3.6.1.4.1.41475.3.1.5.11.2
-- 1.3.6.1.4.1.41475.3.1.4.10.1
-- 1.3.6.1.4.1.41475.3.1.4.10.1
		-- 1.3.6.1.4.1.41475.3.1.4.9.1
		vesdaAlarm OBJECT-TYPE
			SYNTAX DisplayString
			MAX-ACCESS read-only
			STATUS current
			DESCRIPTION
				"Description: Very early warning.
				Reasons: Very early fire detector alarm.
				Values: 0-ok, 1-Alarm"
			::= { vesda 1 }

		
--     1.3.6.1.4.1.41475.3.1.5.11.2
-- 1.3.6.1.4.1.41475.3.1.5.11.2
-- 1.3.6.1.4.1.41475.3.1.4.10.2
-- 1.3.6.1.4.1.41475.3.1.4.10.2
		-- 1.3.6.1.4.1.41475.3.1.4.9.2
		vesdaFire1 OBJECT-TYPE
			SYNTAX DisplayString
			MAX-ACCESS read-only
			STATUS current
			DESCRIPTION
				"Description: Very early fire-1.
				Reasons: Very early fire detector fire-1
				Values: 0-ok, 1-Alarm"
			::= { vesda 2 }

		
--     1.3.6.1.4.1.41475.3.1.5.11.2
-- 1.3.6.1.4.1.41475.3.1.5.11.2
-- 1.3.6.1.4.1.41475.3.1.4.10.3
-- 1.3.6.1.4.1.41475.3.1.4.10.3
		-- 1.3.6.1.4.1.41475.3.1.4.9.3
		vesdaFault OBJECT-TYPE
			SYNTAX DisplayString
			MAX-ACCESS read-only
			STATUS current
			DESCRIPTION
				"Description: Equipment fault.
				Values: 0-ok, 1-fault"
			::= { vesda 3 }

		
--     1.3.6.1.4.1.41475.3.1.5.12
-- 1.3.6.1.4.1.41475.3.1.5.12
-- 1.3.6.1.4.1.41475.3.1.4.11
-- 1.3.6.1.4.1.41475.3.1.4.11
		-- 1.3.6.1.4.1.41475.3.1.4.10
		fireControl OBJECT IDENTIFIER ::= { tmdcMonObjects 10 }

		
--     1.3.6.1.4.1.41475.3.1.5.12.1
-- 1.3.6.1.4.1.41475.3.1.5.12.1
-- 1.3.6.1.4.1.41475.3.1.4.11.1
-- 1.3.6.1.4.1.41475.3.1.4.11.1
		-- 1.3.6.1.4.1.41475.3.1.4.10.1
		fireSmokeSensorState OBJECT-TYPE
			SYNTAX DisplayString
			MAX-ACCESS read-only
			STATUS current
			DESCRIPTION
				"Description: Smoke sensors state
				Reasons: Smoke sensor detects the presence of smoke in the environment, may cause fire.
				Values: 0-ok, 1-Alarm"
			::= { fireControl 1 }

		
--     1.3.6.1.4.1.41475.3.1.5.12.2
-- 1.3.6.1.4.1.41475.3.1.5.12.2
-- 1.3.6.1.4.1.41475.3.1.4.11.3
-- 1.3.6.1.4.1.41475.3.1.4.11.3
		-- 1.3.6.1.4.1.41475.3.1.4.10.2
		fireTempSensorState OBJECT-TYPE
			SYNTAX DisplayString
			MAX-ACCESS read-only
			STATUS current
			DESCRIPTION
				"Description: Temperature sensor state.
				Reasons: The temperature sensor detects high temperature.
				Values: 0-ok, 1-Alarm"
			::= { fireControl 2 }

		
--     1.3.6.1.4.1.41475.3.1.5.13
-- 1.3.6.1.4.1.41475.3.1.5.13
-- 1.3.6.1.4.1.41475.3.1.4.12
-- 1.3.6.1.4.1.41475.3.1.4.12
		-- 1.3.6.1.4.1.41475.3.1.4.11
		entranceGuard OBJECT IDENTIFIER ::= { tmdcMonObjects 11 }

		
--     1.3.6.1.4.1.41475.3.1.5.13.1
-- 1.3.6.1.4.1.41475.3.1.5.13.1
-- 1.3.6.1.4.1.41475.3.1.4.12.1
-- 1.3.6.1.4.1.41475.3.1.4.12.1
		-- 1.3.6.1.4.1.41475.3.1.4.11.1
		entranceDoor1State OBJECT-TYPE
			SYNTAX DisplayString
			MAX-ACCESS read-write
			STATUS current
			DESCRIPTION
				"Description: Door-access 1 State
				Values: 0-close, 1-open"
			::= { entranceGuard 1 }

		
--     1.3.6.1.4.1.41475.3.1.5.13.1
-- 1.3.6.1.4.1.41475.3.1.5.13.1
-- 1.3.6.1.4.1.41475.3.1.4.12.2
-- 1.3.6.1.4.1.41475.3.1.4.12.2
		-- 1.3.6.1.4.1.41475.3.1.4.11.2
		entranceDoor1Alarm OBJECT-TYPE
			SYNTAX DisplayString
			MAX-ACCESS read-only
			STATUS current
			DESCRIPTION
				"Description: Door-access 1 Alarm
				Reasons: Door-access 1 open the door for a long time (>20s) alarm.
				Values: 0-ok, 1-Alarm"
			::= { entranceGuard 2 }

		
--     1.3.6.1.4.1.41475.3.1.5.13.1
-- 1.3.6.1.4.1.41475.3.1.5.13.1
-- 1.3.6.1.4.1.41475.3.1.4.12.4
-- 1.3.6.1.4.1.41475.3.1.4.12.4
		-- 1.3.6.1.4.1.41475.3.1.4.11.3
		entranceDoor2State OBJECT-TYPE
			SYNTAX DisplayString
			MAX-ACCESS read-write
			STATUS current
			DESCRIPTION
				"Description: Door-access 2 State
				Values: 0-close, 1-open"
			::= { entranceGuard 3 }

		
--     1.3.6.1.4.1.41475.3.1.5.13.2
-- 1.3.6.1.4.1.41475.3.1.5.13.2
-- 1.3.6.1.4.1.41475.3.1.4.12.5
-- 1.3.6.1.4.1.41475.3.1.4.12.5
		-- 1.3.6.1.4.1.41475.3.1.4.11.4
		entranceDoor2Alarm OBJECT-TYPE
			SYNTAX DisplayString
			MAX-ACCESS read-only
			STATUS current
			DESCRIPTION
				"Description: Door-access 2 alarm
				Reasons: Door-access 2 open the door for a long time (>20s) alarm.
				Values: 0-ok, 1-Alarm"
			::= { entranceGuard 4 }

		
--  1.3.6.1.4.1.41475.3.1.4.13
		-- 1.3.6.1.4.1.41475.3.1.4.12
		nvr OBJECT IDENTIFIER ::= { tmdcMonObjects 12 }

		
--     1.3.6.1.4.1.41475.3.1.5.12.1
-- 1.3.6.1.4.1.41475.3.1.5.12.1
-- 1.3.6.1.4.1.41475.3.1.4.11.1
-- 1.3.6.1.4.1.41475.3.1.4.13.1
		-- 1.3.6.1.4.1.41475.3.1.4.12.1
		nvrSystemState OBJECT-TYPE
			SYNTAX DisplayString
			MAX-ACCESS read-only
			STATUS current
			DESCRIPTION
				"Description: nvr state
				Values: 0-ok, 1-Alarm"
			::= { nvr 1 }

		
--     1.3.6.1.4.1.41475.3.1.5.12.1
-- 1.3.6.1.4.1.41475.3.1.5.12.1
-- 1.3.6.1.4.1.41475.3.1.4.11.1
-- 1.3.6.1.4.1.41475.3.1.4.13.2
		-- 1.3.6.1.4.1.41475.3.1.4.12.2
		nvrInnerManagerState OBJECT-TYPE
			SYNTAX DisplayString
			MAX-ACCESS read-only
			STATUS current
			DESCRIPTION
				"Description: The camera working state on the side of the control cabinet is installed on the MDC.
				Values: 0-ok, 1-Alarm."
			::= { nvr 2 }

		
--     1.3.6.1.4.1.41475.3.1.5.12.1
-- 1.3.6.1.4.1.41475.3.1.5.12.1
-- 1.3.6.1.4.1.41475.3.1.4.11.1
-- 1.3.6.1.4.1.41475.3.1.4.13.3
		-- 1.3.6.1.4.1.41475.3.1.4.12.3
		nvrInnerRackState OBJECT-TYPE
			SYNTAX DisplayString
			MAX-ACCESS read-only
			STATUS current
			DESCRIPTION
				"Description: The camera working state on the side of the rack is installed on the MDC.
				Values: 0-ok, 1-Alarm."
			::= { nvr 3 }

		
--     1.3.6.1.4.1.41475.3.1.5.12.1
-- 1.3.6.1.4.1.41475.3.1.5.12.1
-- 1.3.6.1.4.1.41475.3.1.4.11.1
-- 1.3.6.1.4.1.41475.3.1.4.13.4
		-- 1.3.6.1.4.1.41475.3.1.4.12.4
		nvrOuterIndexSmallState OBJECT-TYPE
			SYNTAX DisplayString
			MAX-ACCESS read-only
			STATUS current
			DESCRIPTION
				"Description: The camera working state of the MDC external on the side of a big number rack
				
				Values: 0-ok, 1-Alarm."
			::= { nvr 4 }

		
--     1.3.6.1.4.1.41475.3.1.5.12.1
-- 1.3.6.1.4.1.41475.3.1.5.12.1
-- 1.3.6.1.4.1.41475.3.1.4.11.1
-- 1.3.6.1.4.1.41475.3.1.4.13.5
		-- 1.3.6.1.4.1.41475.3.1.4.12.5
		nvrOuterIndexBigState OBJECT-TYPE
			SYNTAX DisplayString
			MAX-ACCESS read-only
			STATUS current
			DESCRIPTION
				"Description: The camera working state of the MDC external on the side of a small number rack
				
				Values: 0-ok, 1-Alarm."
			::= { nvr 5 }

		
--  1.3.6.1.4.1.41475.3.1.4.15
		-- 1.3.6.1.4.1.41475.3.1.4.13
		inverterRack OBJECT IDENTIFIER ::= { tmdcMonObjects 13 }

		
--  1.3.6.1.4.1.41475.3.1.4.15.1
		-- 1.3.6.1.4.1.41475.3.1.4.13.1
		invRackTable OBJECT-TYPE
			SYNTAX SEQUENCE OF InvRackEntry
			MAX-ACCESS not-accessible
			STATUS current
			DESCRIPTION
				"Description."
			::= { inverterRack 1 }

		
--  1.3.6.1.4.1.41475.3.1.4.15.1.1
		-- 1.3.6.1.4.1.41475.3.1.4.13.1.1
		invRackEntry OBJECT-TYPE
			SYNTAX InvRackEntry
			MAX-ACCESS not-accessible
			STATUS current
			DESCRIPTION
				"Description."
			INDEX { invRackIndex }
			::= { invRackTable 1 }

		
		InvRackEntry ::=
			SEQUENCE { 
				invRackIndex
					Integer32,
				invRackLabel
					DisplayString,
				invInDCVoltage
					DisplayString,
				invInACVoltage
					DisplayString,
				invInACFrequency
					DisplayString,
				invOutVoltage
					DisplayString,
				invOutCurrent
					DisplayString,
				invOutPower
					DisplayString,
				invOutLoadrate
					DisplayString,
				invTemperature
					DisplayString,
				invModeSupply
					DisplayString,
				invStatusSupply
					DisplayString,
				invStatusLoad
					DisplayString,
				incStatusACH
					DisplayString,
				invStatusACL
					DisplayString,
				invStatusDCH
					DisplayString,
				invStatusDCL
					DisplayString,
				invStatusHealthy
					DisplayString,
				invStatusRunning
					DisplayString,
				invStatusTemperature
					DisplayString
			 }

--     1.3.6.1.4.1.41475.3.1.5.7.1.1.1
-- 1.3.6.1.4.1.41475.3.1.5.7.1.1.1
-- 1.3.6.1.4.1.41475.3.1.4.6.1.1.1
-- 1.3.6.1.4.1.41475.3.1.4.15.1.1.1
		-- 1.3.6.1.4.1.41475.3.1.4.13.1.1.1
		invRackIndex OBJECT-TYPE
			SYNTAX Integer32 (1..9999)
			MAX-ACCESS read-only
			STATUS current
			DESCRIPTION
				"Description: The serial number, starting from 1"
			::= { invRackEntry 1 }

		
--   1.3.6.1.4.1.41475.3.1.4.6.1.1.2
-- 1.3.6.1.4.1.41475.3.1.4.15.1.1.2
		-- 1.3.6.1.4.1.41475.3.1.4.13.1.1.2
		invRackLabel OBJECT-TYPE
			SYNTAX DisplayString
			MAX-ACCESS read-only
			STATUS current
			DESCRIPTION
				"Description."
			::= { invRackEntry 2 }

		
--   1.3.6.1.4.1.41475.3.1.4.6.1.1.2
-- 1.3.6.1.4.1.41475.3.1.4.15.1.1.3
		-- 1.3.6.1.4.1.41475.3.1.4.13.1.1.3
		invInDCVoltage OBJECT-TYPE
			SYNTAX DisplayString
			UNITS "V"
			MAX-ACCESS read-only
			STATUS current
			DESCRIPTION
				"Description: DC input voltage "
			::= { invRackEntry 3 }

		
--   1.3.6.1.4.1.41475.3.1.4.6.1.1.2
-- 1.3.6.1.4.1.41475.3.1.4.15.1.1.4
		-- 1.3.6.1.4.1.41475.3.1.4.13.1.1.4
		invInACVoltage OBJECT-TYPE
			SYNTAX DisplayString
			UNITS "V"
			MAX-ACCESS read-only
			STATUS current
			DESCRIPTION
				"Description: AC input voltage "
			::= { invRackEntry 4 }

		
--   1.3.6.1.4.1.41475.3.1.4.6.1.1.2
-- 1.3.6.1.4.1.41475.3.1.4.15.1.1.5
		-- 1.3.6.1.4.1.41475.3.1.4.13.1.1.5
		invInACFrequency OBJECT-TYPE
			SYNTAX DisplayString
			UNITS "Hz"
			MAX-ACCESS read-only
			STATUS current
			DESCRIPTION
				"Description: AC input frequency."
			::= { invRackEntry 5 }

		
--   1.3.6.1.4.1.41475.3.1.4.6.1.1.2
-- 1.3.6.1.4.1.41475.3.1.4.15.1.1.6
		-- 1.3.6.1.4.1.41475.3.1.4.13.1.1.6
		invOutVoltage OBJECT-TYPE
			SYNTAX DisplayString
			UNITS "V"
			MAX-ACCESS read-only
			STATUS current
			DESCRIPTION
				"Description: output voltage."
			::= { invRackEntry 6 }

		
--   1.3.6.1.4.1.41475.3.1.4.6.1.1.2
-- 1.3.6.1.4.1.41475.3.1.4.15.1.1.7
		-- 1.3.6.1.4.1.41475.3.1.4.13.1.1.7
		invOutCurrent OBJECT-TYPE
			SYNTAX DisplayString
			UNITS "A"
			MAX-ACCESS read-only
			STATUS current
			DESCRIPTION
				"Description: output current."
			::= { invRackEntry 7 }

		
--   1.3.6.1.4.1.41475.3.1.4.6.1.1.2
-- 1.3.6.1.4.1.41475.3.1.4.15.1.1.8
		-- 1.3.6.1.4.1.41475.3.1.4.13.1.1.8
		invOutPower OBJECT-TYPE
			SYNTAX DisplayString
			UNITS "kW"
			MAX-ACCESS read-only
			STATUS current
			DESCRIPTION
				"Description: output power."
			::= { invRackEntry 8 }

		
--   1.3.6.1.4.1.41475.3.1.4.6.1.1.2
-- 1.3.6.1.4.1.41475.3.1.4.15.1.1.9
		-- 1.3.6.1.4.1.41475.3.1.4.13.1.1.9
		invOutLoadrate OBJECT-TYPE
			SYNTAX DisplayString
			UNITS "%"
			MAX-ACCESS read-only
			STATUS current
			DESCRIPTION
				"Description: output loadrate."
			::= { invRackEntry 9 }

		
--   1.3.6.1.4.1.41475.3.1.4.6.1.1.2
-- 1.3.6.1.4.1.41475.3.1.4.15.1.1.10
		-- 1.3.6.1.4.1.41475.3.1.4.13.1.1.10
		invTemperature OBJECT-TYPE
			SYNTAX DisplayString
			UNITS "¡æ"
			MAX-ACCESS read-only
			STATUS current
			DESCRIPTION
				"Description: Internal radiator temperature "
			::= { invRackEntry 10 }

		
--   1.3.6.1.4.1.41475.3.1.4.6.1.1.2
-- 1.3.6.1.4.1.41475.3.1.4.15.1.1.11
		-- 1.3.6.1.4.1.41475.3.1.4.13.1.1.11
		invModeSupply OBJECT-TYPE
			SYNTAX DisplayString
			MAX-ACCESS read-only
			STATUS current
			DESCRIPTION
				"Description: supply mode.
				Values: 0- DC main supply, 1- AC main supply."
			::= { invRackEntry 11 }

		
--   1.3.6.1.4.1.41475.3.1.4.6.1.1.2
-- 1.3.6.1.4.1.41475.3.1.4.15.1.1.12
		-- 1.3.6.1.4.1.41475.3.1.4.13.1.1.12
		invStatusSupply OBJECT-TYPE
			SYNTAX DisplayString
			MAX-ACCESS read-only
			STATUS current
			DESCRIPTION
				"Description: Current state of power supply.
				
				Values: 0-inverter, 1-bypass."
			::= { invRackEntry 12 }

		
--   1.3.6.1.4.1.41475.3.1.4.6.1.1.2
-- 1.3.6.1.4.1.41475.3.1.4.15.1.1.13
		-- 1.3.6.1.4.1.41475.3.1.4.13.1.1.13
		invStatusLoad OBJECT-TYPE
			SYNTAX DisplayString
			MAX-ACCESS read-only
			STATUS current
			DESCRIPTION
				"Description: Overload state 
				
				Values: 0-ok, 1-alarm."
			::= { invRackEntry 13 }

		
--   1.3.6.1.4.1.41475.3.1.4.6.1.1.2
-- 1.3.6.1.4.1.41475.3.1.4.15.1.1.14
		-- 1.3.6.1.4.1.41475.3.1.4.13.1.1.14
		incStatusACH OBJECT-TYPE
			SYNTAX DisplayString
			MAX-ACCESS read-only
			STATUS current
			DESCRIPTION
				"Description: AC input voltage is too high 
				Values: 0-ok, 1-alarm."
			::= { invRackEntry 14 }

		
--   1.3.6.1.4.1.41475.3.1.4.6.1.1.2
-- 1.3.6.1.4.1.41475.3.1.4.15.1.1.15
		-- 1.3.6.1.4.1.41475.3.1.4.13.1.1.15
		invStatusACL OBJECT-TYPE
			SYNTAX DisplayString
			MAX-ACCESS read-only
			STATUS current
			DESCRIPTION
				"Description: AC input voltage is too low.
				Values: 0-ok, 1-alarm."
			::= { invRackEntry 15 }

		
--   1.3.6.1.4.1.41475.3.1.4.6.1.1.2
-- 1.3.6.1.4.1.41475.3.1.4.15.1.1.16
		-- 1.3.6.1.4.1.41475.3.1.4.13.1.1.16
		invStatusDCH OBJECT-TYPE
			SYNTAX DisplayString
			MAX-ACCESS read-only
			STATUS current
			DESCRIPTION
				"Description: DC input voltage is too high 
				Values: 0-ok, 1-alarm"
			::= { invRackEntry 16 }

		
--   1.3.6.1.4.1.41475.3.1.4.6.1.1.2
-- 1.3.6.1.4.1.41475.3.1.4.15.1.1.17
		-- 1.3.6.1.4.1.41475.3.1.4.13.1.1.17
		invStatusDCL OBJECT-TYPE
			SYNTAX DisplayString
			MAX-ACCESS read-only
			STATUS current
			DESCRIPTION
				"Description: DC input voltage is too low.
				Values: 0-ok, 1-alarm."
			::= { invRackEntry 17 }

		
--   1.3.6.1.4.1.41475.3.1.4.6.1.1.2
-- 1.3.6.1.4.1.41475.3.1.4.15.1.1.18
		-- 1.3.6.1.4.1.41475.3.1.4.13.1.1.18
		invStatusHealthy OBJECT-TYPE
			SYNTAX DisplayString
			MAX-ACCESS read-only
			STATUS current
			DESCRIPTION
				"Description: healthy status
				
				Values: 0-ok, 1-Alarm."
			::= { invRackEntry 18 }

		
--   1.3.6.1.4.1.41475.3.1.4.6.1.1.2
-- 1.3.6.1.4.1.41475.3.1.4.15.1.1.19
		-- 1.3.6.1.4.1.41475.3.1.4.13.1.1.19
		invStatusRunning OBJECT-TYPE
			SYNTAX DisplayString
			MAX-ACCESS read-only
			STATUS current
			DESCRIPTION
				"Description: running status
				
				Values: 0-open, 1-close."
			::= { invRackEntry 19 }

		
		-- 1.3.6.1.4.1.41475.3.1.4.13.1.1.20
		invStatusTemperature OBJECT-TYPE
			SYNTAX DisplayString
			MAX-ACCESS read-write
			STATUS current
			DESCRIPTION
				"Description.Internal radiator temperature alarm status 
				
				Values: 0-ok, 1-alarm."
			::= { invRackEntry 20 }

		
		-- 1.3.6.1.4.1.41475.3.1.4.14
		ups OBJECT IDENTIFIER ::= { tmdcMonObjects 14 }

		
		-- 1.3.6.1.4.1.41475.3.1.4.14.1
		upsSystemTable OBJECT-TYPE
			SYNTAX SEQUENCE OF UpsSystemEntry
			MAX-ACCESS not-accessible
			STATUS current
			DESCRIPTION
				"Description."
			::= { ups 1 }

		
		-- 1.3.6.1.4.1.41475.3.1.4.14.1.1
		upsSystemEntry OBJECT-TYPE
			SYNTAX UpsSystemEntry
			MAX-ACCESS not-accessible
			STATUS current
			DESCRIPTION
				"Description."
			INDEX { upsSystemIndex }
			::= { upsSystemTable 1 }

		
		UpsSystemEntry ::=
			SEQUENCE { 
				upsSystemIndex
					Integer32,
				upsInputVoltageA
					DisplayString,
				upsInputVoltageB
					DisplayString,
				upsInputVoltageC
					DisplayString,
				upsInputCurrentA
					DisplayString,
				upsInputCurrentB
					DisplayString,
				upsInputCurrentC
					DisplayString,
				upsInputFrequency
					DisplayString,
				upsInputActivePowerTotal
					DisplayString,
				upsInputActivePowerA
					DisplayString,
				upsInputActivePowerB
					DisplayString,
				upsInputActivePowerC
					DisplayString,
				upsInputLoadFactorTotal
					DisplayString,
				upsInputLoadFactorA
					DisplayString,
				upsInputtLoadFactorB
					DisplayString,
				upsInputLoadFactorC
					DisplayString,
				upsBypassVoltageA
					DisplayString,
				upsBypassVoltageB
					DisplayString,
				upsBypassVoltageC
					DisplayString,
				upsBypassCurrentA
					DisplayString,
				upsBypassCurrentB
					DisplayString,
				upsBypassCurrentC
					DisplayString,
				upsBypassFrequency
					DisplayString,
				upsBypassActivePowerTotal
					DisplayString,
				upsBypassActivePowerA
					DisplayString,
				upsBypassActivePowerB
					DisplayString,
				upsBypassActivePowerC
					DisplayString,
				upsOutputVoltageA
					DisplayString,
				upsOutputVoltageB
					DisplayString,
				upsOutputVoltageC
					DisplayString,
				upsOutputCurrentA
					DisplayString,
				upsOutputCurrentB
					DisplayString,
				upsOutputCurrentC
					DisplayString,
				upsOutputFrequency
					DisplayString,
				upsOutputActivePowerTotal
					DisplayString,
				upsOutputActivePowerA
					DisplayString,
				upsOutputActivePowerB
					DisplayString,
				upsOutputActivePowerC
					DisplayString,
				upsOutputLoadFactorTotal
					DisplayString,
				upsOutputLoadFactorA
					DisplayString,
				upsOutputLoadFactorB
					DisplayString,
				upsOutputLoadFactorC
					DisplayString,
				upsOutputLoadrateA
					DisplayString,
				upsOutputLoadrateB
					DisplayString,
				upsOutputLoadrateC
					DisplayString,
				upsBatVoltage
					DisplayString,
				upsBatCurrent
					DisplayString,
				upsBatCapacity
					DisplayString,
				upsOutputMode
					DisplayString,
				upsInputBreakerStatus
					DisplayString,
				upsBypassBreakerStatus
					DisplayString,
				upsMaintainBreakerStatus
					DisplayString,
				upsOutputBreakerStatus
					DisplayString,
				upsBatBreakerStatus
					DisplayString,
				upsBatWorkingState
					DisplayString,
				upsInputFilterState
					DisplayString,
				upsInputFault
					DisplayString,
				upsBypassFault
					DisplayString,
				upsRectifierFault
					DisplayString,
				upsInverterFault
					DisplayString,
				upsFuseFault
					DisplayString,
				upsFanFault
					DisplayString,
				upsBatteryFault
					DisplayString,
				upsWorkStatusAlarm
					DisplayString,
				upsCircuitBreakerFault
					DisplayString,
				upsOutputFault
					DisplayString,
				upsGeneralAlarm
					DisplayString
			 }

		-- 1.3.6.1.4.1.41475.3.1.4.14.1.1.1
		upsSystemIndex OBJECT-TYPE
			SYNTAX Integer32 (1..2)
			MAX-ACCESS read-only
			STATUS current
			DESCRIPTION
				"Description."
			::= { upsSystemEntry 1 }

		
		-- 1.3.6.1.4.1.41475.3.1.4.14.1.1.2
		upsInputVoltageA OBJECT-TYPE
			SYNTAX DisplayString
			UNITS "V"
			MAX-ACCESS read-only
			STATUS current
			DESCRIPTION
				"Description."
			::= { upsSystemEntry 2 }

		
		-- 1.3.6.1.4.1.41475.3.1.4.14.1.1.3
		upsInputVoltageB OBJECT-TYPE
			SYNTAX DisplayString
			UNITS "V"
			MAX-ACCESS read-only
			STATUS current
			DESCRIPTION
				"Description."
			::= { upsSystemEntry 3 }

		
		-- 1.3.6.1.4.1.41475.3.1.4.14.1.1.4
		upsInputVoltageC OBJECT-TYPE
			SYNTAX DisplayString
			UNITS "V"
			MAX-ACCESS read-only
			STATUS current
			DESCRIPTION
				"Description."
			::= { upsSystemEntry 4 }

		
		-- 1.3.6.1.4.1.41475.3.1.4.14.1.1.5
		upsInputCurrentA OBJECT-TYPE
			SYNTAX DisplayString
			UNITS "A"
			MAX-ACCESS read-only
			STATUS current
			DESCRIPTION
				"Description."
			::= { upsSystemEntry 5 }

		
		-- 1.3.6.1.4.1.41475.3.1.4.14.1.1.6
		upsInputCurrentB OBJECT-TYPE
			SYNTAX DisplayString
			UNITS "A"
			MAX-ACCESS read-only
			STATUS current
			DESCRIPTION
				"Description."
			::= { upsSystemEntry 6 }

		
		-- 1.3.6.1.4.1.41475.3.1.4.14.1.1.7
		upsInputCurrentC OBJECT-TYPE
			SYNTAX DisplayString
			UNITS "A"
			MAX-ACCESS read-only
			STATUS current
			DESCRIPTION
				"Description."
			::= { upsSystemEntry 7 }

		
		-- 1.3.6.1.4.1.41475.3.1.4.14.1.1.8
		upsInputFrequency OBJECT-TYPE
			SYNTAX DisplayString
			UNITS "Hz"
			MAX-ACCESS read-only
			STATUS current
			DESCRIPTION
				"Description."
			::= { upsSystemEntry 8 }

		
		-- 1.3.6.1.4.1.41475.3.1.4.14.1.1.9
		upsInputActivePowerTotal OBJECT-TYPE
			SYNTAX DisplayString
			UNITS "kW"
			MAX-ACCESS read-only
			STATUS current
			DESCRIPTION
				"Description."
			::= { upsSystemEntry 9 }

		
		-- 1.3.6.1.4.1.41475.3.1.4.14.1.1.10
		upsInputActivePowerA OBJECT-TYPE
			SYNTAX DisplayString
			UNITS "kW"
			MAX-ACCESS read-only
			STATUS current
			DESCRIPTION
				"Description."
			::= { upsSystemEntry 10 }

		
		-- 1.3.6.1.4.1.41475.3.1.4.14.1.1.11
		upsInputActivePowerB OBJECT-TYPE
			SYNTAX DisplayString
			UNITS "kW"
			MAX-ACCESS read-only
			STATUS current
			DESCRIPTION
				"Description."
			::= { upsSystemEntry 11 }

		
		-- 1.3.6.1.4.1.41475.3.1.4.14.1.1.12
		upsInputActivePowerC OBJECT-TYPE
			SYNTAX DisplayString
			UNITS "kW"
			MAX-ACCESS read-only
			STATUS current
			DESCRIPTION
				"Description."
			::= { upsSystemEntry 12 }

		
		-- 1.3.6.1.4.1.41475.3.1.4.14.1.1.13
		upsInputLoadFactorTotal OBJECT-TYPE
			SYNTAX DisplayString
			MAX-ACCESS read-only
			STATUS current
			DESCRIPTION
				"Description."
			::= { upsSystemEntry 13 }

		
		-- 1.3.6.1.4.1.41475.3.1.4.14.1.1.14
		upsInputLoadFactorA OBJECT-TYPE
			SYNTAX DisplayString
			MAX-ACCESS read-only
			STATUS current
			DESCRIPTION
				"Description."
			::= { upsSystemEntry 14 }

		
		-- 1.3.6.1.4.1.41475.3.1.4.14.1.1.15
		upsInputtLoadFactorB OBJECT-TYPE
			SYNTAX DisplayString
			MAX-ACCESS read-only
			STATUS current
			DESCRIPTION
				"Description."
			::= { upsSystemEntry 15 }

		
		-- 1.3.6.1.4.1.41475.3.1.4.14.1.1.16
		upsInputLoadFactorC OBJECT-TYPE
			SYNTAX DisplayString
			MAX-ACCESS read-only
			STATUS current
			DESCRIPTION
				"Description."
			::= { upsSystemEntry 16 }

		
		-- 1.3.6.1.4.1.41475.3.1.4.14.1.1.17
		upsBypassVoltageA OBJECT-TYPE
			SYNTAX DisplayString
			UNITS "V"
			MAX-ACCESS read-only
			STATUS current
			DESCRIPTION
				"Description."
			::= { upsSystemEntry 17 }

		
		-- 1.3.6.1.4.1.41475.3.1.4.14.1.1.18
		upsBypassVoltageB OBJECT-TYPE
			SYNTAX DisplayString
			UNITS "V"
			MAX-ACCESS read-only
			STATUS current
			DESCRIPTION
				"Description."
			::= { upsSystemEntry 18 }

		
		-- 1.3.6.1.4.1.41475.3.1.4.14.1.1.19
		upsBypassVoltageC OBJECT-TYPE
			SYNTAX DisplayString
			UNITS "V"
			MAX-ACCESS read-only
			STATUS current
			DESCRIPTION
				"Description."
			::= { upsSystemEntry 19 }

		
		-- 1.3.6.1.4.1.41475.3.1.4.14.1.1.20
		upsBypassCurrentA OBJECT-TYPE
			SYNTAX DisplayString
			UNITS "A"
			MAX-ACCESS read-only
			STATUS current
			DESCRIPTION
				"Description."
			::= { upsSystemEntry 20 }

		
		-- 1.3.6.1.4.1.41475.3.1.4.14.1.1.21
		upsBypassCurrentB OBJECT-TYPE
			SYNTAX DisplayString
			UNITS "A"
			MAX-ACCESS read-only
			STATUS current
			DESCRIPTION
				"Description."
			::= { upsSystemEntry 21 }

		
		-- 1.3.6.1.4.1.41475.3.1.4.14.1.1.22
		upsBypassCurrentC OBJECT-TYPE
			SYNTAX DisplayString
			UNITS "A"
			MAX-ACCESS read-only
			STATUS current
			DESCRIPTION
				"Description."
			::= { upsSystemEntry 22 }

		
		-- 1.3.6.1.4.1.41475.3.1.4.14.1.1.23
		upsBypassFrequency OBJECT-TYPE
			SYNTAX DisplayString
			UNITS "Hz"
			MAX-ACCESS read-only
			STATUS current
			DESCRIPTION
				"Description."
			::= { upsSystemEntry 23 }

		
		-- 1.3.6.1.4.1.41475.3.1.4.14.1.1.24
		upsBypassActivePowerTotal OBJECT-TYPE
			SYNTAX DisplayString
			UNITS "kW"
			MAX-ACCESS read-only
			STATUS current
			DESCRIPTION
				"Description."
			::= { upsSystemEntry 24 }

		
		-- 1.3.6.1.4.1.41475.3.1.4.14.1.1.25
		upsBypassActivePowerA OBJECT-TYPE
			SYNTAX DisplayString
			UNITS "kW"
			MAX-ACCESS read-only
			STATUS current
			DESCRIPTION
				"Description."
			::= { upsSystemEntry 25 }

		
		-- 1.3.6.1.4.1.41475.3.1.4.14.1.1.26
		upsBypassActivePowerB OBJECT-TYPE
			SYNTAX DisplayString
			UNITS "kW"
			MAX-ACCESS read-only
			STATUS current
			DESCRIPTION
				"Description."
			::= { upsSystemEntry 26 }

		
		-- 1.3.6.1.4.1.41475.3.1.4.14.1.1.27
		upsBypassActivePowerC OBJECT-TYPE
			SYNTAX DisplayString
			UNITS "kW"
			MAX-ACCESS read-only
			STATUS current
			DESCRIPTION
				"Description."
			::= { upsSystemEntry 27 }

		
		-- 1.3.6.1.4.1.41475.3.1.4.14.1.1.28
		upsOutputVoltageA OBJECT-TYPE
			SYNTAX DisplayString
			UNITS "V"
			MAX-ACCESS read-only
			STATUS current
			DESCRIPTION
				"Description."
			::= { upsSystemEntry 28 }

		
		-- 1.3.6.1.4.1.41475.3.1.4.14.1.1.29
		upsOutputVoltageB OBJECT-TYPE
			SYNTAX DisplayString
			UNITS "V"
			MAX-ACCESS read-only
			STATUS current
			DESCRIPTION
				"Description."
			::= { upsSystemEntry 29 }

		
		-- 1.3.6.1.4.1.41475.3.1.4.14.1.1.30
		upsOutputVoltageC OBJECT-TYPE
			SYNTAX DisplayString
			UNITS "V"
			MAX-ACCESS read-only
			STATUS current
			DESCRIPTION
				"Description."
			::= { upsSystemEntry 30 }

		
		-- 1.3.6.1.4.1.41475.3.1.4.14.1.1.31
		upsOutputCurrentA OBJECT-TYPE
			SYNTAX DisplayString
			UNITS "A"
			MAX-ACCESS read-only
			STATUS current
			DESCRIPTION
				"Description."
			::= { upsSystemEntry 31 }

		
		-- 1.3.6.1.4.1.41475.3.1.4.14.1.1.32
		upsOutputCurrentB OBJECT-TYPE
			SYNTAX DisplayString
			UNITS "A"
			MAX-ACCESS read-only
			STATUS current
			DESCRIPTION
				"Description."
			::= { upsSystemEntry 32 }

		
		-- 1.3.6.1.4.1.41475.3.1.4.14.1.1.33
		upsOutputCurrentC OBJECT-TYPE
			SYNTAX DisplayString
			UNITS "A"
			MAX-ACCESS read-only
			STATUS current
			DESCRIPTION
				"Description."
			::= { upsSystemEntry 33 }

		
		-- 1.3.6.1.4.1.41475.3.1.4.14.1.1.34
		upsOutputFrequency OBJECT-TYPE
			SYNTAX DisplayString
			UNITS "Hz"
			MAX-ACCESS read-only
			STATUS current
			DESCRIPTION
				"Description."
			::= { upsSystemEntry 34 }

		
		-- 1.3.6.1.4.1.41475.3.1.4.14.1.1.35
		upsOutputActivePowerTotal OBJECT-TYPE
			SYNTAX DisplayString
			UNITS "kW"
			MAX-ACCESS read-only
			STATUS current
			DESCRIPTION
				"Description."
			::= { upsSystemEntry 35 }

		
		-- 1.3.6.1.4.1.41475.3.1.4.14.1.1.36
		upsOutputActivePowerA OBJECT-TYPE
			SYNTAX DisplayString
			UNITS "kW"
			MAX-ACCESS read-only
			STATUS current
			DESCRIPTION
				"Description."
			::= { upsSystemEntry 36 }

		
		-- 1.3.6.1.4.1.41475.3.1.4.14.1.1.37
		upsOutputActivePowerB OBJECT-TYPE
			SYNTAX DisplayString
			UNITS "kW"
			MAX-ACCESS read-only
			STATUS current
			DESCRIPTION
				"Description."
			::= { upsSystemEntry 37 }

		
		-- 1.3.6.1.4.1.41475.3.1.4.14.1.1.38
		upsOutputActivePowerC OBJECT-TYPE
			SYNTAX DisplayString
			UNITS "kW"
			MAX-ACCESS read-only
			STATUS current
			DESCRIPTION
				"Description."
			::= { upsSystemEntry 38 }

		
		-- 1.3.6.1.4.1.41475.3.1.4.14.1.1.39
		upsOutputLoadFactorTotal OBJECT-TYPE
			SYNTAX DisplayString
			MAX-ACCESS read-only
			STATUS current
			DESCRIPTION
				"Description."
			::= { upsSystemEntry 39 }

		
		-- 1.3.6.1.4.1.41475.3.1.4.14.1.1.40
		upsOutputLoadFactorA OBJECT-TYPE
			SYNTAX DisplayString
			MAX-ACCESS read-only
			STATUS current
			DESCRIPTION
				"Description."
			::= { upsSystemEntry 40 }

		
		-- 1.3.6.1.4.1.41475.3.1.4.14.1.1.41
		upsOutputLoadFactorB OBJECT-TYPE
			SYNTAX DisplayString
			MAX-ACCESS read-only
			STATUS current
			DESCRIPTION
				"Description."
			::= { upsSystemEntry 41 }

		
		-- 1.3.6.1.4.1.41475.3.1.4.14.1.1.42
		upsOutputLoadFactorC OBJECT-TYPE
			SYNTAX DisplayString
			MAX-ACCESS read-only
			STATUS current
			DESCRIPTION
				"Description."
			::= { upsSystemEntry 42 }

		
		-- 1.3.6.1.4.1.41475.3.1.4.14.1.1.43
		upsOutputLoadrateA OBJECT-TYPE
			SYNTAX DisplayString
			UNITS "%"
			MAX-ACCESS read-only
			STATUS current
			DESCRIPTION
				"Description."
			::= { upsSystemEntry 43 }

		
		-- 1.3.6.1.4.1.41475.3.1.4.14.1.1.44
		upsOutputLoadrateB OBJECT-TYPE
			SYNTAX DisplayString
			UNITS "%"
			MAX-ACCESS read-only
			STATUS current
			DESCRIPTION
				"Description."
			::= { upsSystemEntry 44 }

		
		-- 1.3.6.1.4.1.41475.3.1.4.14.1.1.45
		upsOutputLoadrateC OBJECT-TYPE
			SYNTAX DisplayString
			UNITS "%"
			MAX-ACCESS read-only
			STATUS current
			DESCRIPTION
				"Description."
			::= { upsSystemEntry 45 }

		
		-- 1.3.6.1.4.1.41475.3.1.4.14.1.1.46
		upsBatVoltage OBJECT-TYPE
			SYNTAX DisplayString
			UNITS "V"
			MAX-ACCESS read-only
			STATUS current
			DESCRIPTION
				"Description."
			::= { upsSystemEntry 46 }

		
		-- 1.3.6.1.4.1.41475.3.1.4.14.1.1.47
		upsBatCurrent OBJECT-TYPE
			SYNTAX DisplayString
			UNITS "A"
			MAX-ACCESS read-only
			STATUS current
			DESCRIPTION
				"Description."
			::= { upsSystemEntry 47 }

		
		-- 1.3.6.1.4.1.41475.3.1.4.14.1.1.48
		upsBatCapacity OBJECT-TYPE
			SYNTAX DisplayString
			UNITS "%"
			MAX-ACCESS read-only
			STATUS current
			DESCRIPTION
				"Description."
			::= { upsSystemEntry 48 }

		
		-- 1.3.6.1.4.1.41475.3.1.4.14.1.1.49
		upsOutputMode OBJECT-TYPE
			SYNTAX DisplayString
			MAX-ACCESS read-only
			STATUS current
			DESCRIPTION
				"Description."
			::= { upsSystemEntry 49 }

		
		-- 1.3.6.1.4.1.41475.3.1.4.14.1.1.50
		upsInputBreakerStatus OBJECT-TYPE
			SYNTAX DisplayString
			MAX-ACCESS read-only
			STATUS current
			DESCRIPTION
				"Description."
			::= { upsSystemEntry 50 }

		
		-- 1.3.6.1.4.1.41475.3.1.4.14.1.1.51
		upsBypassBreakerStatus OBJECT-TYPE
			SYNTAX DisplayString
			MAX-ACCESS read-only
			STATUS current
			DESCRIPTION
				"Description."
			::= { upsSystemEntry 51 }

		
		-- 1.3.6.1.4.1.41475.3.1.4.14.1.1.52
		upsMaintainBreakerStatus OBJECT-TYPE
			SYNTAX DisplayString
			MAX-ACCESS read-only
			STATUS current
			DESCRIPTION
				"Description."
			::= { upsSystemEntry 52 }

		
		-- 1.3.6.1.4.1.41475.3.1.4.14.1.1.53
		upsOutputBreakerStatus OBJECT-TYPE
			SYNTAX DisplayString
			MAX-ACCESS read-only
			STATUS current
			DESCRIPTION
				"Description."
			::= { upsSystemEntry 53 }

		
		-- 1.3.6.1.4.1.41475.3.1.4.14.1.1.54
		upsBatBreakerStatus OBJECT-TYPE
			SYNTAX DisplayString
			MAX-ACCESS read-only
			STATUS current
			DESCRIPTION
				"Description."
			::= { upsSystemEntry 54 }

		
		-- 1.3.6.1.4.1.41475.3.1.4.14.1.1.55
		upsBatWorkingState OBJECT-TYPE
			SYNTAX DisplayString
			MAX-ACCESS read-only
			STATUS current
			DESCRIPTION
				"Description."
			::= { upsSystemEntry 55 }

		
		-- 1.3.6.1.4.1.41475.3.1.4.14.1.1.56
		upsInputFilterState OBJECT-TYPE
			SYNTAX DisplayString
			MAX-ACCESS read-only
			STATUS current
			DESCRIPTION
				"Description."
			::= { upsSystemEntry 56 }

		
		-- 1.3.6.1.4.1.41475.3.1.4.14.1.1.57
		upsInputFault OBJECT-TYPE
			SYNTAX DisplayString
			MAX-ACCESS read-only
			STATUS current
			DESCRIPTION
				"Description."
			::= { upsSystemEntry 57 }

		
		-- 1.3.6.1.4.1.41475.3.1.4.14.1.1.58
		upsBypassFault OBJECT-TYPE
			SYNTAX DisplayString
			MAX-ACCESS read-only
			STATUS current
			DESCRIPTION
				"Description."
			::= { upsSystemEntry 58 }

		
		-- 1.3.6.1.4.1.41475.3.1.4.14.1.1.59
		upsRectifierFault OBJECT-TYPE
			SYNTAX DisplayString
			MAX-ACCESS read-only
			STATUS current
			DESCRIPTION
				"Description."
			::= { upsSystemEntry 59 }

		
		-- 1.3.6.1.4.1.41475.3.1.4.14.1.1.60
		upsInverterFault OBJECT-TYPE
			SYNTAX DisplayString
			MAX-ACCESS read-only
			STATUS current
			DESCRIPTION
				"Description."
			::= { upsSystemEntry 60 }

		
		-- 1.3.6.1.4.1.41475.3.1.4.14.1.1.61
		upsFuseFault OBJECT-TYPE
			SYNTAX DisplayString
			MAX-ACCESS read-only
			STATUS current
			DESCRIPTION
				"Description."
			::= { upsSystemEntry 61 }

		
		-- 1.3.6.1.4.1.41475.3.1.4.14.1.1.62
		upsFanFault OBJECT-TYPE
			SYNTAX DisplayString
			MAX-ACCESS read-only
			STATUS current
			DESCRIPTION
				"Description."
			::= { upsSystemEntry 62 }

		
		-- 1.3.6.1.4.1.41475.3.1.4.14.1.1.63
		upsBatteryFault OBJECT-TYPE
			SYNTAX DisplayString
			MAX-ACCESS read-only
			STATUS current
			DESCRIPTION
				"Description."
			::= { upsSystemEntry 63 }

		
		-- 1.3.6.1.4.1.41475.3.1.4.14.1.1.64
		upsWorkStatusAlarm OBJECT-TYPE
			SYNTAX DisplayString
			MAX-ACCESS read-only
			STATUS current
			DESCRIPTION
				"Description."
			::= { upsSystemEntry 64 }

		
		-- 1.3.6.1.4.1.41475.3.1.4.14.1.1.65
		upsCircuitBreakerFault OBJECT-TYPE
			SYNTAX DisplayString
			MAX-ACCESS read-only
			STATUS current
			DESCRIPTION
				"Description."
			::= { upsSystemEntry 65 }

		
		-- 1.3.6.1.4.1.41475.3.1.4.14.1.1.66
		upsOutputFault OBJECT-TYPE
			SYNTAX DisplayString
			MAX-ACCESS read-only
			STATUS current
			DESCRIPTION
				"Description."
			::= { upsSystemEntry 66 }

		
		-- 1.3.6.1.4.1.41475.3.1.4.14.1.1.67
		upsGeneralAlarm OBJECT-TYPE
			SYNTAX DisplayString
			MAX-ACCESS read-only
			STATUS current
			DESCRIPTION
				"Description."
			::= { upsSystemEntry 67 }

		
		-- 1.3.6.1.4.1.41475.3.1.4.14.2
		upsModuleTable OBJECT-TYPE
			SYNTAX SEQUENCE OF UpsModuleEntry
			MAX-ACCESS not-accessible
			STATUS current
			DESCRIPTION
				"Description."
			::= { ups 2 }

		
		-- 1.3.6.1.4.1.41475.3.1.4.14.2.1
		upsModuleEntry OBJECT-TYPE
			SYNTAX UpsModuleEntry
			MAX-ACCESS not-accessible
			STATUS current
			DESCRIPTION
				"Description."
			INDEX { upsModuleIndex }
			::= { upsModuleTable 1 }

		
		UpsModuleEntry ::=
			SEQUENCE { 
				upsModuleIndex
					Integer32,
				upsModuleOuputVoltageA
					DisplayString,
				upsModuleOuputVoltageB
					DisplayString,
				upsModuleOuputVoltageC
					DisplayString,
				upsModuleOutputCurrentA
					DisplayString,
				upsModuleOutputCurrentB
					DisplayString,
				upsModuleOutputCurrentC
					DisplayString,
				upsModuleOutputActivePowerA
					DisplayString,
				upsModuleOutputActivePowerB
					DisplayString,
				upsModuleOutputActivePowerC
					DisplayString,
				upsModuleOutputApparentPowerA
					DisplayString,
				upsModuleOutputApparentPowerB
					DisplayString,
				upsModuleOutputApparentPowerC
					DisplayString,
				upsModuleOutputLoadFactorA
					DisplayString,
				upsModuleOutputLoadFactorB
					DisplayString,
				upsModuleOutputLoadFactorC
					DisplayString,
				upsModuleOutputFrequency
					DisplayString,
				upsModuleWorkingState
					DisplayString
			 }

		-- 1.3.6.1.4.1.41475.3.1.4.14.2.1.1
		upsModuleIndex OBJECT-TYPE
			SYNTAX Integer32 (1..2)
			MAX-ACCESS read-only
			STATUS current
			DESCRIPTION
				"Description."
			::= { upsModuleEntry 1 }

		
		-- 1.3.6.1.4.1.41475.3.1.4.14.2.1.2
		upsModuleOuputVoltageA OBJECT-TYPE
			SYNTAX DisplayString
			UNITS "V"
			MAX-ACCESS read-only
			STATUS current
			DESCRIPTION
				"Description."
			::= { upsModuleEntry 2 }

		
		-- 1.3.6.1.4.1.41475.3.1.4.14.2.1.3
		upsModuleOuputVoltageB OBJECT-TYPE
			SYNTAX DisplayString
			UNITS "V"
			MAX-ACCESS read-only
			STATUS current
			DESCRIPTION
				"Description."
			::= { upsModuleEntry 3 }

		
		-- 1.3.6.1.4.1.41475.3.1.4.14.2.1.4
		upsModuleOuputVoltageC OBJECT-TYPE
			SYNTAX DisplayString
			UNITS "V"
			MAX-ACCESS read-only
			STATUS current
			DESCRIPTION
				"Description."
			::= { upsModuleEntry 4 }

		
		-- 1.3.6.1.4.1.41475.3.1.4.14.2.1.5
		upsModuleOutputCurrentA OBJECT-TYPE
			SYNTAX DisplayString
			UNITS "A"
			MAX-ACCESS read-only
			STATUS current
			DESCRIPTION
				"Description."
			::= { upsModuleEntry 5 }

		
		-- 1.3.6.1.4.1.41475.3.1.4.14.2.1.6
		upsModuleOutputCurrentB OBJECT-TYPE
			SYNTAX DisplayString
			UNITS "A"
			MAX-ACCESS read-only
			STATUS current
			DESCRIPTION
				"Description."
			::= { upsModuleEntry 6 }

		
		-- 1.3.6.1.4.1.41475.3.1.4.14.2.1.7
		upsModuleOutputCurrentC OBJECT-TYPE
			SYNTAX DisplayString
			UNITS "A"
			MAX-ACCESS read-only
			STATUS current
			DESCRIPTION
				"Description."
			::= { upsModuleEntry 7 }

		
		-- 1.3.6.1.4.1.41475.3.1.4.14.2.1.8
		upsModuleOutputActivePowerA OBJECT-TYPE
			SYNTAX DisplayString
			UNITS "kW"
			MAX-ACCESS read-only
			STATUS current
			DESCRIPTION
				"Description."
			::= { upsModuleEntry 8 }

		
		-- 1.3.6.1.4.1.41475.3.1.4.14.2.1.9
		upsModuleOutputActivePowerB OBJECT-TYPE
			SYNTAX DisplayString
			UNITS "kW"
			MAX-ACCESS read-only
			STATUS current
			DESCRIPTION
				"Description."
			::= { upsModuleEntry 9 }

		
		-- 1.3.6.1.4.1.41475.3.1.4.14.2.1.10
		upsModuleOutputActivePowerC OBJECT-TYPE
			SYNTAX DisplayString
			UNITS "kW"
			MAX-ACCESS read-only
			STATUS current
			DESCRIPTION
				"Description."
			::= { upsModuleEntry 10 }

		
		-- 1.3.6.1.4.1.41475.3.1.4.14.2.1.11
		upsModuleOutputApparentPowerA OBJECT-TYPE
			SYNTAX DisplayString
			UNITS "kVA"
			MAX-ACCESS read-only
			STATUS current
			DESCRIPTION
				"Description."
			::= { upsModuleEntry 11 }

		
		-- 1.3.6.1.4.1.41475.3.1.4.14.2.1.12
		upsModuleOutputApparentPowerB OBJECT-TYPE
			SYNTAX DisplayString
			UNITS "kVA"
			MAX-ACCESS read-only
			STATUS current
			DESCRIPTION
				"Description."
			::= { upsModuleEntry 12 }

		
		-- 1.3.6.1.4.1.41475.3.1.4.14.2.1.13
		upsModuleOutputApparentPowerC OBJECT-TYPE
			SYNTAX DisplayString
			UNITS "kVA"
			MAX-ACCESS read-only
			STATUS current
			DESCRIPTION
				"Description."
			::= { upsModuleEntry 13 }

		
		-- 1.3.6.1.4.1.41475.3.1.4.14.2.1.14
		upsModuleOutputLoadFactorA OBJECT-TYPE
			SYNTAX DisplayString
			MAX-ACCESS read-only
			STATUS current
			DESCRIPTION
				"Description."
			::= { upsModuleEntry 14 }

		
		-- 1.3.6.1.4.1.41475.3.1.4.14.2.1.15
		upsModuleOutputLoadFactorB OBJECT-TYPE
			SYNTAX DisplayString
			MAX-ACCESS read-only
			STATUS current
			DESCRIPTION
				"Description."
			::= { upsModuleEntry 15 }

		
		-- 1.3.6.1.4.1.41475.3.1.4.14.2.1.16
		upsModuleOutputLoadFactorC OBJECT-TYPE
			SYNTAX DisplayString
			MAX-ACCESS read-only
			STATUS current
			DESCRIPTION
				"Description."
			::= { upsModuleEntry 16 }

		
		-- 1.3.6.1.4.1.41475.3.1.4.14.2.1.17
		upsModuleOutputFrequency OBJECT-TYPE
			SYNTAX DisplayString
			UNITS "Hz"
			MAX-ACCESS read-only
			STATUS current
			DESCRIPTION
				"Description."
			::= { upsModuleEntry 17 }

		
		-- 1.3.6.1.4.1.41475.3.1.4.14.2.1.18
		upsModuleWorkingState OBJECT-TYPE
			SYNTAX DisplayString
			MAX-ACCESS read-only
			STATUS current
			DESCRIPTION
				"Description."
			::= { upsModuleEntry 18 }

		
		-- 1.3.6.1.4.1.41475.3.1.4.15
		busway OBJECT IDENTIFIER ::= { tmdcMonObjects 15 }

		
		-- 1.3.6.1.4.1.41475.3.1.4.15.1
		buswayATempTable OBJECT-TYPE
			SYNTAX SEQUENCE OF BuswayATempEntry
			MAX-ACCESS not-accessible
			STATUS current
			DESCRIPTION
				"Description."
			::= { busway 1 }

		
		-- 1.3.6.1.4.1.41475.3.1.4.15.1.1
		buswayATempEntry OBJECT-TYPE
			SYNTAX BuswayATempEntry
			MAX-ACCESS not-accessible
			STATUS current
			DESCRIPTION
				"Description."
			INDEX { buswayATempIndex }
			::= { buswayATempTable 1 }

		
		BuswayATempEntry ::=
			SEQUENCE { 
				buswayATempIndex
					Integer32,
				buswayATempJointpoint
					DisplayString
			 }

		-- 1.3.6.1.4.1.41475.3.1.4.15.1.1.1
		buswayATempIndex OBJECT-TYPE
			SYNTAX Integer32 (1..100)
			MAX-ACCESS read-only
			STATUS current
			DESCRIPTION
				"Description."
			::= { buswayATempEntry 1 }

		
		-- 1.3.6.1.4.1.41475.3.1.4.15.1.1.2
		buswayATempJointpoint OBJECT-TYPE
			SYNTAX DisplayString
			UNITS "¡æ"
			MAX-ACCESS read-only
			STATUS current
			DESCRIPTION
				"Description."
			::= { buswayATempEntry 2 }

		
		-- 1.3.6.1.4.1.41475.3.1.4.15.2
		buswayBTempTable OBJECT-TYPE
			SYNTAX SEQUENCE OF BuswayBTempEntry
			MAX-ACCESS not-accessible
			STATUS current
			DESCRIPTION
				"Description."
			::= { busway 2 }

		
		-- 1.3.6.1.4.1.41475.3.1.4.15.2.1
		buswayBTempEntry OBJECT-TYPE
			SYNTAX BuswayBTempEntry
			MAX-ACCESS not-accessible
			STATUS current
			DESCRIPTION
				"Description."
			INDEX { buswayBTempIndex }
			::= { buswayBTempTable 1 }

		
		BuswayBTempEntry ::=
			SEQUENCE { 
				buswayBTempIndex
					Integer32,
				buswayBTempJointpoint
					DisplayString
			 }

		-- 1.3.6.1.4.1.41475.3.1.4.15.2.1.1
		buswayBTempIndex OBJECT-TYPE
			SYNTAX Integer32 (1..100)
			MAX-ACCESS read-only
			STATUS current
			DESCRIPTION
				"Description."
			::= { buswayBTempEntry 1 }

		
		-- 1.3.6.1.4.1.41475.3.1.4.15.2.1.2
		buswayBTempJointpoint OBJECT-TYPE
			SYNTAX DisplayString
			UNITS "¡æ"
			MAX-ACCESS read-only
			STATUS current
			DESCRIPTION
				"Description."
			::= { buswayBTempEntry 2 }

		
--   1.3.6.1.4.1.41475.3.1.5
-- 1.3.6.1.4.1.41475.3.1.6
		-- 1.3.6.1.4.1.41475.3.1.5
		tmdcMonDevice OBJECT IDENTIFIER ::= { tmdc 5 }

		
--   1.3.6.1.4.1.41475.3.1.5.1
-- 1.3.6.1.4.1.41475.3.1.6.1
		-- 1.3.6.1.4.1.41475.3.1.5.1
		server OBJECT IDENTIFIER ::= { tmdcMonDevice 1 }

		
--   1.3.6.1.4.1.41475.3.1.5.1.1
-- 1.3.6.1.4.1.41475.3.1.6.1.1
		-- 1.3.6.1.4.1.41475.3.1.5.1.1
		serverCoreNumber OBJECT-TYPE
			SYNTAX DisplayString
			MAX-ACCESS read-only
			STATUS current
			DESCRIPTION
				"Description."
			::= { server 1 }

		
--   Description: The number of CPU core
-- 1.3.6.1.4.1.41475.3.1.5.1.2
-- 1.3.6.1.4.1.41475.3.1.6.1.2
		-- 1.3.6.1.4.1.41475.3.1.5.1.2
		serverCPULoad OBJECT-TYPE
			SYNTAX DisplayString
			UNITS "%"
			MAX-ACCESS read-only
			STATUS current
			DESCRIPTION
				"Description: CPU load percentage.
				"
			::= { server 2 }

		
--   1.3.6.1.4.1.41475.3.1.5.1.3
-- 1.3.6.1.4.1.41475.3.1.6.1.3
		-- 1.3.6.1.4.1.41475.3.1.5.1.3
		serverMemTotal OBJECT-TYPE
			SYNTAX DisplayString
			UNITS "MB"
			MAX-ACCESS read-only
			STATUS current
			DESCRIPTION
				"Description: Total physical memory."
			::= { server 3 }

		
--   1.3.6.1.4.1.41475.3.1.5.1.4
-- 1.3.6.1.4.1.41475.3.1.6.1.4
		-- 1.3.6.1.4.1.41475.3.1.5.1.4
		serverMemAvailable OBJECT-TYPE
			SYNTAX DisplayString
			UNITS "MB"
			MAX-ACCESS read-only
			STATUS current
			DESCRIPTION
				"Description: Total physical memory available."
			::= { server 4 }

		
--   1.3.6.1.4.1.41475.3.1.5.1.5
-- 1.3.6.1.4.1.41475.3.1.6.1.5
		-- 1.3.6.1.4.1.41475.3.1.5.1.5
		serverDiskTotal OBJECT-TYPE
			SYNTAX DisplayString
			UNITS "GB"
			MAX-ACCESS read-only
			STATUS current
			DESCRIPTION
				"Description: The total size of the hard disk.
				"
			::= { server 5 }

		
--   1.3.6.1.4.1.41475.3.1.5.1.6
-- 1.3.6.1.4.1.41475.3.1.6.1.6
		-- 1.3.6.1.4.1.41475.3.1.5.1.6
		serverDiskAvailable OBJECT-TYPE
			SYNTAX DisplayString
			UNITS "GB"
			MAX-ACCESS read-only
			STATUS current
			DESCRIPTION
				"Description: Available hard disk size."
			::= { server 6 }

		
--   1.3.6.1.4.1.41475.3.1.5.1.7
-- 1.3.6.1.4.1.41475.3.1.6.1.7
		-- 1.3.6.1.4.1.41475.3.1.5.1.7
		serverNetworkUpwardSpeed OBJECT-TYPE
			SYNTAX DisplayString
			UNITS "KB/s"
			MAX-ACCESS read-only
			STATUS current
			DESCRIPTION
				"Description: Real-time upward speed.
				"
			::= { server 7 }

		
--   1.3.6.1.4.1.41475.3.1.5.1.8
-- 1.3.6.1.4.1.41475.3.1.6.1.8
		-- 1.3.6.1.4.1.41475.3.1.5.1.8
		serverNetworkDownwardSpeed OBJECT-TYPE
			SYNTAX DisplayString
			UNITS "KB/s"
			MAX-ACCESS read-only
			STATUS current
			DESCRIPTION
				"Description: Real-time downward speed."
			::= { server 8 }

		
--   1.3.6.1.4.1.41475.3.1.5.1.9
-- 1.3.6.1.4.1.41475.3.1.6.1.9
		-- 1.3.6.1.4.1.41475.3.1.5.1.9
		serverNetworkUpwardTotal OBJECT-TYPE
			SYNTAX DisplayString
			UNITS "MB"
			MAX-ACCESS read-only
			STATUS current
			DESCRIPTION
				"Description: Network upward total flow."
			::= { server 9 }

		
--   1.3.6.1.4.1.41475.3.1.5.1.10
-- 1.3.6.1.4.1.41475.3.1.6.1.10
		-- 1.3.6.1.4.1.41475.3.1.5.1.10
		serverNetworkDownwardTotal OBJECT-TYPE
			SYNTAX DisplayString
			UNITS "MB"
			MAX-ACCESS read-only
			STATUS current
			DESCRIPTION
				"Description: Network downward total flow."
			::= { server 10 }

		
--   1.3.6.1.4.1.41475.3.1.5.2
-- 1.3.6.1.4.1.41475.3.1.6.2
		-- 1.3.6.1.4.1.41475.3.1.5.2
		switch OBJECT IDENTIFIER ::= { tmdcMonDevice 2 }

		
--   1.3.6.1.4.1.41475.3.1.5.2.1
-- 1.3.6.1.4.1.41475.3.1.6.2.1
		-- 1.3.6.1.4.1.41475.3.1.5.2.1
		switchWorkState OBJECT-TYPE
			SYNTAX DisplayString
			MAX-ACCESS read-only
			STATUS current
			DESCRIPTION
				"Description: Switch working state.
				Values: 0-ok, 1-Alarm"
			::= { switch 1 }

		
--   1.3.6.1.4.1.41475.3.1.5.2.2
-- 1.3.6.1.4.1.41475.3.1.6.2.2
		-- 1.3.6.1.4.1.41475.3.1.5.2.2
		switchPortTable OBJECT-TYPE
			SYNTAX SEQUENCE OF SwitchPortEntry
			MAX-ACCESS not-accessible
			STATUS current
			DESCRIPTION
				"Description."
			::= { switch 2 }

		
--   1.3.6.1.4.1.41475.3.1.5.2.2.1
-- 1.3.6.1.4.1.41475.3.1.6.2.2.1
		-- 1.3.6.1.4.1.41475.3.1.5.2.2.1
		switchPortEntry OBJECT-TYPE
			SYNTAX SwitchPortEntry
			MAX-ACCESS not-accessible
			STATUS current
			DESCRIPTION
				"Description."
			INDEX { switchPortIndex }
			::= { switchPortTable 1 }

		
		SwitchPortEntry ::=
			SEQUENCE { 
				switchPortIndex
					Integer32,
				switchPortState
					DisplayString,
				switchPortFlowTotal
					DisplayString
			 }

--   1.3.6.1.4.1.41475.3.1.5.2.2.1.1
-- 1.3.6.1.4.1.41475.3.1.6.2.2.1.1
		-- 1.3.6.1.4.1.41475.3.1.5.2.2.1.1
		switchPortIndex OBJECT-TYPE
			SYNTAX Integer32 (1..9999)
			MAX-ACCESS read-only
			STATUS current
			DESCRIPTION
				"Description: The serial number, starting from 1"
			::= { switchPortEntry 1 }

		
--   1.3.6.1.4.1.41475.3.1.5.2.2.1.2
-- 1.3.6.1.4.1.41475.3.1.6.2.2.1.2
		-- 1.3.6.1.4.1.41475.3.1.5.2.2.1.2
		switchPortState OBJECT-TYPE
			SYNTAX DisplayString
			MAX-ACCESS read-only
			STATUS current
			DESCRIPTION
				"Description: Switch port working state.
				Values: 0-ok, 1-Alarm"
			::= { switchPortEntry 2 }

		
--   1.3.6.1.4.1.41475.3.1.5.2.2.1.3
-- 1.3.6.1.4.1.41475.3.1.6.2.2.1.3
		-- 1.3.6.1.4.1.41475.3.1.5.2.2.1.3
		switchPortFlowTotal OBJECT-TYPE
			SYNTAX DisplayString
			UNITS "MB"
			MAX-ACCESS read-only
			STATUS current
			DESCRIPTION
				"Description: Switch port flow."
			::= { switchPortEntry 3 }

		
--   1.3.6.1.4.1.41475.3.1.5.3
-- 1.3.6.1.4.1.41475.3.1.6.3
		-- 1.3.6.1.4.1.41475.3.1.5.3
		collector OBJECT IDENTIFIER ::= { tmdcMonDevice 3 }

		
--   1.3.6.1.4.1.41475.3.1.5.3.1
-- 1.3.6.1.4.1.41475.3.1.6.3.1
		-- 1.3.6.1.4.1.41475.3.1.5.3.1
		collectorWorkState OBJECT-TYPE
			SYNTAX DisplayString
			MAX-ACCESS read-only
			STATUS current
			DESCRIPTION
				"Description: Switch working state.
				Values: 0-ok, 1-Alarm"
			::= { collector 1 }

		
--   1.3.6.1.4.1.41475.3.1.5.3.2
-- 1.3.6.1.4.1.41475.3.1.6.3.2
		-- 1.3.6.1.4.1.41475.3.1.5.3.2
		collectorNetworkUpwardTotal OBJECT-TYPE
			SYNTAX DisplayString
			UNITS "MB"
			MAX-ACCESS read-only
			STATUS current
			DESCRIPTION
				"Description: Network upward total flow."
			::= { collector 2 }

		
--   1.3.6.1.4.1.41475.3.1.5.3.3
-- 1.3.6.1.4.1.41475.3.1.6.3.3
		-- 1.3.6.1.4.1.41475.3.1.5.3.3
		collectorNetworkDownwardTotal OBJECT-TYPE
			SYNTAX DisplayString
			UNITS "MB"
			MAX-ACCESS read-only
			STATUS current
			DESCRIPTION
				"Description: Network downward total flow."
			::= { collector 3 }

		
--   1.3.6.1.4.1.41475.3.1.5.3.4
-- 1.3.6.1.4.1.41475.3.1.6.3.4
		-- 1.3.6.1.4.1.41475.3.1.5.3.4
		collectorCOMTable OBJECT-TYPE
			SYNTAX SEQUENCE OF CollectorCOMEntry
			MAX-ACCESS not-accessible
			STATUS current
			DESCRIPTION
				"Description."
			::= { collector 4 }

		
--   1.3.6.1.4.1.41475.3.1.5.3.4.1
-- 1.3.6.1.4.1.41475.3.1.6.3.4.1
		-- 1.3.6.1.4.1.41475.3.1.5.3.4.1
		collectorCOMEntry OBJECT-TYPE
			SYNTAX CollectorCOMEntry
			MAX-ACCESS not-accessible
			STATUS current
			DESCRIPTION
				"Description."
			INDEX { collectorCOMIndex }
			::= { collectorCOMTable 1 }

		
		CollectorCOMEntry ::=
			SEQUENCE { 
				collectorCOMIndex
					Integer32,
				collectorCOMState
					DisplayString
			 }

--   1.3.6.1.4.1.41475.3.1.5.3.4.1.1
-- 1.3.6.1.4.1.41475.3.1.6.3.4.1.1
		-- 1.3.6.1.4.1.41475.3.1.5.3.4.1.1
		collectorCOMIndex OBJECT-TYPE
			SYNTAX Integer32 (1..9999)
			MAX-ACCESS read-only
			STATUS current
			DESCRIPTION
				"Description: The serial number, starting from 1"
			::= { collectorCOMEntry 1 }

		
--   1.3.6.1.4.1.41475.3.1.5.3.4.1.2
-- 1.3.6.1.4.1.41475.3.1.6.3.4.1.2
		-- 1.3.6.1.4.1.41475.3.1.5.3.4.1.2
		collectorCOMState OBJECT-TYPE
			SYNTAX DisplayString
			MAX-ACCESS read-only
			STATUS current
			DESCRIPTION
				"Description: Collector COM port working state.
				Values: 0-ok, 1-Alarm"
			::= { collectorCOMEntry 2 }

		
--   1.3.6.1.4.1.41475.3.1.5.3.5
-- 1.3.6.1.4.1.41475.3.1.6.3.5
		-- 1.3.6.1.4.1.41475.3.1.5.3.5
		collectorDITable OBJECT-TYPE
			SYNTAX SEQUENCE OF CollectorDIEntry
			MAX-ACCESS not-accessible
			STATUS current
			DESCRIPTION
				"Description."
			::= { collector 5 }

		
--   1.3.6.1.4.1.41475.3.1.5.3.5.1
-- 1.3.6.1.4.1.41475.3.1.6.3.5.1
		-- 1.3.6.1.4.1.41475.3.1.5.3.5.1
		collectorDIEntry OBJECT-TYPE
			SYNTAX CollectorDIEntry
			MAX-ACCESS not-accessible
			STATUS current
			DESCRIPTION
				"Description."
			INDEX { collectorDCIndex }
			::= { collectorDITable 1 }

		
		CollectorDIEntry ::=
			SEQUENCE { 
				collectorDIIndex
					Integer32,
				collectorDIState
					DisplayString
			 }

--   1.3.6.1.4.1.41475.3.1.5.3.5.1.1
-- 1.3.6.1.4.1.41475.3.1.6.3.5.1.1
		-- 1.3.6.1.4.1.41475.3.1.5.3.5.1.1
		collectorDIIndex OBJECT-TYPE
			SYNTAX Integer32 (1..9999)
			MAX-ACCESS read-only
			STATUS current
			DESCRIPTION
				"Description: The DI number, starting from 1"
			::= { collectorDIEntry 1 }

		
--   1.3.6.1.4.1.41475.3.1.5.3.5.1.2
-- 1.3.6.1.4.1.41475.3.1.6.3.5.1.2
		-- 1.3.6.1.4.1.41475.3.1.5.3.5.1.2
		collectorDIState OBJECT-TYPE
			SYNTAX DisplayString
			MAX-ACCESS read-only
			STATUS current
			DESCRIPTION
				"Description: Collector DI working state.
				Values: 0-ok, 1-Alarm"
			::= { collectorDIEntry 2 }

		
--   1.3.6.1.4.1.41475.3.1.5.3.6
-- 1.3.6.1.4.1.41475.3.1.6.3.6
		-- 1.3.6.1.4.1.41475.3.1.5.3.6
		collectorDOTable OBJECT-TYPE
			SYNTAX SEQUENCE OF CollectorDOEntry
			MAX-ACCESS not-accessible
			STATUS current
			DESCRIPTION
				"Description."
			::= { collector 6 }

		
--   1.3.6.1.4.1.41475.3.1.5.3.6.1
-- 1.3.6.1.4.1.41475.3.1.6.3.6.1
		-- 1.3.6.1.4.1.41475.3.1.5.3.6.1
		collectorDOEntry OBJECT-TYPE
			SYNTAX CollectorDOEntry
			MAX-ACCESS not-accessible
			STATUS current
			DESCRIPTION
				"Description."
			INDEX { collectorDCIndex }
			::= { collectorDOTable 1 }

		
		CollectorDOEntry ::=
			SEQUENCE { 
				collectorDOIndex
					Integer32,
				collectorDOState
					DisplayString
			 }

--   1.3.6.1.4.1.41475.3.1.5.3.6.1.1
-- 1.3.6.1.4.1.41475.3.1.6.3.6.1.1
		-- 1.3.6.1.4.1.41475.3.1.5.3.6.1.1
		collectorDOIndex OBJECT-TYPE
			SYNTAX Integer32 (1..9999)
			MAX-ACCESS read-only
			STATUS current
			DESCRIPTION
				"Description: The DO number, starting from 1"
			::= { collectorDOEntry 1 }

		
--   1.3.6.1.4.1.41475.3.1.5.3.6.1.2
-- 1.3.6.1.4.1.41475.3.1.6.3.6.1.2
		-- 1.3.6.1.4.1.41475.3.1.5.3.6.1.2
		collectorDOState OBJECT-TYPE
			SYNTAX DisplayString
			MAX-ACCESS read-only
			STATUS current
			DESCRIPTION
				"Description: Collector DO working state.
				Values: 0-ok, 1-Alarm"
			::= { collectorDOEntry 2 }

		
--   1.3.6.1.4.1.41475.3.1.5.3.7
-- 1.3.6.1.4.1.41475.3.1.6.3.7
		-- 1.3.6.1.4.1.41475.3.1.5.3.7
		collectorDCTable OBJECT-TYPE
			SYNTAX SEQUENCE OF CollectorDCEntry
			MAX-ACCESS not-accessible
			STATUS current
			DESCRIPTION
				"Description."
			::= { collector 7 }

		
--   1.3.6.1.4.1.41475.3.1.5.3.7.1
-- 1.3.6.1.4.1.41475.3.1.6.3.7.1
		-- 1.3.6.1.4.1.41475.3.1.5.3.7.1
		collectorDCEntry OBJECT-TYPE
			SYNTAX CollectorDCEntry
			MAX-ACCESS not-accessible
			STATUS current
			DESCRIPTION
				"Description."
			INDEX { collectorDCIndex }
			::= { collectorDCTable 1 }

		
		CollectorDCEntry ::=
			SEQUENCE { 
				collectorDCIndex
					Integer32,
				collectorDCState
					DisplayString
			 }

--   1.3.6.1.4.1.41475.3.1.5.3.7.1.1
-- 1.3.6.1.4.1.41475.3.1.6.3.7.1.1
		-- 1.3.6.1.4.1.41475.3.1.5.3.7.1.1
		collectorDCIndex OBJECT-TYPE
			SYNTAX Integer32 (1..9999)
			MAX-ACCESS read-only
			STATUS current
			DESCRIPTION
				"Description: The DC number, starting from 1"
			::= { collectorDCEntry 1 }

		
--   1.3.6.1.4.1.41475.3.1.5.3.7.1.2
-- 1.3.6.1.4.1.41475.3.1.6.3.7.1.2
		-- 1.3.6.1.4.1.41475.3.1.5.3.7.1.2
		collectorDCState OBJECT-TYPE
			SYNTAX DisplayString
			MAX-ACCESS read-only
			STATUS current
			DESCRIPTION
				"Description: Collector DC working state.
				Values: 0-ok, 1-Alarm"
			::= { collectorDCEntry 2 }

		
--  1.3.6.1.4.1.41475.3.1.4.14
		-- 1.3.6.1.4.1.41475.3.1.5.4
		inverterMGT OBJECT IDENTIFIER ::= { tmdcMonDevice 4 }

		
--   1.3.6.1.4.1.41475.3.1.4.1.1
-- 1.3.6.1.4.1.41475.3.1.4.14.1
		-- 1.3.6.1.4.1.41475.3.1.5.4.1
		inDCVoltage OBJECT-TYPE
			SYNTAX DisplayString
			UNITS "V"
			MAX-ACCESS read-only
			STATUS current
			DESCRIPTION
				"Description: DC input voltage "
			::= { inverterMGT 1 }

		
--   1.3.6.1.4.1.41475.3.1.4.1.1
-- 1.3.6.1.4.1.41475.3.1.4.14.2
		-- 1.3.6.1.4.1.41475.3.1.5.4.2
		inACVoltage OBJECT-TYPE
			SYNTAX DisplayString
			UNITS "V"
			MAX-ACCESS read-only
			STATUS current
			DESCRIPTION
				"Description: AC input voltage "
			::= { inverterMGT 2 }

		
--   1.3.6.1.4.1.41475.3.1.4.1.1
-- 1.3.6.1.4.1.41475.3.1.4.14.3
		-- 1.3.6.1.4.1.41475.3.1.5.4.3
		inACFrequency OBJECT-TYPE
			SYNTAX DisplayString
			UNITS "Hz"
			MAX-ACCESS read-only
			STATUS current
			DESCRIPTION
				"Description: AC input frequency."
			::= { inverterMGT 3 }

		
--   1.3.6.1.4.1.41475.3.1.4.1.1
-- 1.3.6.1.4.1.41475.3.1.4.14.4
		-- 1.3.6.1.4.1.41475.3.1.5.4.4
		outVoltage OBJECT-TYPE
			SYNTAX DisplayString
			UNITS "V"
			MAX-ACCESS read-only
			STATUS current
			DESCRIPTION
				"Description: output voltage."
			::= { inverterMGT 4 }

		
--   1.3.6.1.4.1.41475.3.1.4.1.1
-- 1.3.6.1.4.1.41475.3.1.4.14.5
		-- 1.3.6.1.4.1.41475.3.1.5.4.5
		outCurrent OBJECT-TYPE
			SYNTAX DisplayString
			UNITS "A"
			MAX-ACCESS read-only
			STATUS current
			DESCRIPTION
				"Description: output current."
			::= { inverterMGT 5 }

		
--   1.3.6.1.4.1.41475.3.1.4.1.1
-- 1.3.6.1.4.1.41475.3.1.4.14.6
		-- 1.3.6.1.4.1.41475.3.1.5.4.6
		outPower OBJECT-TYPE
			SYNTAX DisplayString
			UNITS "kW"
			MAX-ACCESS read-only
			STATUS current
			DESCRIPTION
				"Description: output power."
			::= { inverterMGT 6 }

		
--   1.3.6.1.4.1.41475.3.1.4.1.1
-- 1.3.6.1.4.1.41475.3.1.4.14.7
		-- 1.3.6.1.4.1.41475.3.1.5.4.7
		outLoadrate OBJECT-TYPE
			SYNTAX DisplayString
			UNITS "%"
			MAX-ACCESS read-only
			STATUS current
			DESCRIPTION
				"Description: output loadrate."
			::= { inverterMGT 7 }

		
--   1.3.6.1.4.1.41475.3.1.4.1.1
-- 1.3.6.1.4.1.41475.3.1.4.14.8
		-- 1.3.6.1.4.1.41475.3.1.5.4.8
		temperature OBJECT-TYPE
			SYNTAX DisplayString
			UNITS "¡æ"
			MAX-ACCESS read-only
			STATUS current
			DESCRIPTION
				"Description: Internal radiator temperature."
			::= { inverterMGT 8 }

		
--     1.3.6.1.4.1.41475.3.1.5.12.1
-- 1.3.6.1.4.1.41475.3.1.5.12.1
-- 1.3.6.1.4.1.41475.3.1.4.11.1
-- 1.3.6.1.4.1.41475.3.1.4.14.9
		-- 1.3.6.1.4.1.41475.3.1.5.4.9
		modeSupply OBJECT-TYPE
			SYNTAX DisplayString
			MAX-ACCESS read-only
			STATUS current
			DESCRIPTION
				"Description: supply mode.
				Values: 0- DC main supply, 1- AC main supply."
			::= { inverterMGT 9 }

		
--     1.3.6.1.4.1.41475.3.1.5.12.1
-- 1.3.6.1.4.1.41475.3.1.5.12.1
-- 1.3.6.1.4.1.41475.3.1.4.11.1
-- 1.3.6.1.4.1.41475.3.1.4.14.10
		-- 1.3.6.1.4.1.41475.3.1.5.4.10
		statusSupply OBJECT-TYPE
			SYNTAX DisplayString
			MAX-ACCESS read-only
			STATUS current
			DESCRIPTION
				"Description: Current state of power supply.
				
				Values: 0-inverter, 1-bypass."
			::= { inverterMGT 10 }

		
--     1.3.6.1.4.1.41475.3.1.5.12.1
-- 1.3.6.1.4.1.41475.3.1.5.12.1
-- 1.3.6.1.4.1.41475.3.1.4.11.1
-- 1.3.6.1.4.1.41475.3.1.4.14.11
		-- 1.3.6.1.4.1.41475.3.1.5.4.11
		statusLoad OBJECT-TYPE
			SYNTAX DisplayString
			MAX-ACCESS read-only
			STATUS current
			DESCRIPTION
				"Description: Overload state 
				
				Values: 0-ok, 1-alarm."
			::= { inverterMGT 11 }

		
--     1.3.6.1.4.1.41475.3.1.5.12.1
-- 1.3.6.1.4.1.41475.3.1.5.12.1
-- 1.3.6.1.4.1.41475.3.1.4.11.1
-- 1.3.6.1.4.1.41475.3.1.4.14.12
		-- 1.3.6.1.4.1.41475.3.1.5.4.12
		statusACH OBJECT-TYPE
			SYNTAX DisplayString
			MAX-ACCESS read-only
			STATUS current
			DESCRIPTION
				"Description: AC input voltage is too high 
				Values: 0-ok, 1-alarm."
			::= { inverterMGT 12 }

		
--     1.3.6.1.4.1.41475.3.1.5.12.1
-- 1.3.6.1.4.1.41475.3.1.5.12.1
-- 1.3.6.1.4.1.41475.3.1.4.11.1
-- 1.3.6.1.4.1.41475.3.1.4.14.13
		-- 1.3.6.1.4.1.41475.3.1.5.4.13
		statusACL OBJECT-TYPE
			SYNTAX DisplayString
			MAX-ACCESS read-only
			STATUS current
			DESCRIPTION
				"Description: AC input voltage is too low.
				Values: 0-ok, 1-alarm."
			::= { inverterMGT 13 }

		
--     1.3.6.1.4.1.41475.3.1.5.12.1
-- 1.3.6.1.4.1.41475.3.1.5.12.1
-- 1.3.6.1.4.1.41475.3.1.4.11.1
-- 1.3.6.1.4.1.41475.3.1.4.14.14
		-- 1.3.6.1.4.1.41475.3.1.5.4.14
		statusDCH OBJECT-TYPE
			SYNTAX DisplayString
			MAX-ACCESS read-only
			STATUS current
			DESCRIPTION
				"Description: DC input voltage is too high 
				Values: 0-ok, 1-alarm."
			::= { inverterMGT 14 }

		
--     1.3.6.1.4.1.41475.3.1.5.12.1
-- 1.3.6.1.4.1.41475.3.1.5.12.1
-- 1.3.6.1.4.1.41475.3.1.4.11.1
-- 1.3.6.1.4.1.41475.3.1.4.14.15
		-- 1.3.6.1.4.1.41475.3.1.5.4.15
		statusDCL OBJECT-TYPE
			SYNTAX DisplayString
			MAX-ACCESS read-only
			STATUS current
			DESCRIPTION
				"Description: DC input voltage is too low.
				Values: 0-ok, 1-alarm."
			::= { inverterMGT 15 }

		
--     1.3.6.1.4.1.41475.3.1.5.12.1
-- 1.3.6.1.4.1.41475.3.1.5.12.1
-- 1.3.6.1.4.1.41475.3.1.4.11.1
-- 1.3.6.1.4.1.41475.3.1.4.14.16
		-- 1.3.6.1.4.1.41475.3.1.5.4.16
		statusHealthy OBJECT-TYPE
			SYNTAX DisplayString
			MAX-ACCESS read-only
			STATUS current
			DESCRIPTION
				"Description: healthy status
				
				Values: 0-ok, 1-Alarm."
			::= { inverterMGT 16 }

		
--     1.3.6.1.4.1.41475.3.1.5.12.1
-- 1.3.6.1.4.1.41475.3.1.5.12.1
-- 1.3.6.1.4.1.41475.3.1.4.11.1
-- 1.3.6.1.4.1.41475.3.1.4.14.17
		-- 1.3.6.1.4.1.41475.3.1.5.4.17
		statusRunning OBJECT-TYPE
			SYNTAX DisplayString
			MAX-ACCESS read-only
			STATUS current
			DESCRIPTION
				"Description: running status
				
				Values: 0-open, 1-close."
			::= { inverterMGT 17 }

		
--     1.3.6.1.4.1.41475.3.1.5.12.1
-- 1.3.6.1.4.1.41475.3.1.5.12.1
-- 1.3.6.1.4.1.41475.3.1.4.11.1
-- 1.3.6.1.4.1.41475.3.1.4.14.17
		-- 1.3.6.1.4.1.41475.3.1.5.4.18
		statusTemperature OBJECT-TYPE
			SYNTAX DisplayString
			MAX-ACCESS read-only
			STATUS current
			DESCRIPTION
				"Description: Internal radiator temperature alarm status 
				
				Values: 0-ok, 1-alarm."
			::= { inverterMGT 18 }

		
	
	END

--
-- TENCENT-TMDC-MIB_V3.0.6.mib
--
